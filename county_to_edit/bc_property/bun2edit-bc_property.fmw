FME workspace bun2edit-bc_property.fmw

Parameters:
- DestDataset_POSTGIS = coa-pg-db1-datastore1   # Connection

Readers:
- GEODATABASE_SDE_1: GEODATABASE_SDE

Writers:
- POSTGIS_1: POSTGIS to $(DestDataset_POSTGIS)

DBO.PROPERTY (reader GEODATABASE_SDE_1)
    attributes: objectid integer, pinnum char(15), pin char(10), pinext char(5), owner char(100), nmptype integer, TaxYear char(2), CondoUnit char(5), CondoBuilding char(10), DeedBook char(4), DeedPage char(4), PlatBook char(4), PlatPage char(4), SubName char(35), SubLot char(30), SubBlock char(5), SubSect char(2), UpdateDate char(8), HouseNumber char(5), NumberSuffix char(4), direction char(2), streetname char(30), StreetType char(4), Township char(2), Acreage double, AccountNumber char(1073741822), DeedDate char(8), Stamps double, Instrument char(3), Reason char(1),
      County char(3), City char(3), FireDistrict char(3), SchoolDistrict char(3), CareOf char(30), Address char(100), CityName char(100), State char(2), Zipcode char(10), Class char(10), Improved char(1), Exempt char(3), Priced char(1), TotalMarketValue integer, AppraisedValue integer, TaxValue integer, LandUse char(10), NeighborhoodCode char(7), LandValue integer, BuildingValue integer, ImprovementValue integer, AppraisalArea char(1), PostDirection char(2), SalePrice double, propcard char(150), shape.STArea() double, shape.STLength() double
    -> ownertrim
ownertrim: AttributeTrimmer
    TRIM_TYPE = Both
    SRC_ATTRS = owner
    TRIM_TO_NONE = Yes
    -> coagis.bc_property (writer POSTGIS_1)
coagis.bc_property (writer POSTGIS_1)
    attributes: objectid int4, pinnum varchar(15), pin varchar(10), pinext varchar(5), owner varchar(100), nmptype int4, taxyear varchar(2), condounit varchar(5), condobuilding varchar(10), deedbook varchar(4), deedpage varchar(4), platbook varchar(4), platpage varchar(4), subname varchar(35), sublot varchar(30), subblock varchar(5), subsect varchar(2), updatedate varchar(8), housenumber varchar(5), numbersuffix varchar(4), direction varchar(2), streetname varchar(30), streettype varchar(4), township varchar(2), acreage float8, accountnumber varchar(1073741822), deeddate varchar(8), stamps float8, instrument varchar(3), reason varchar(1),
      county varchar(3), city varchar(3), firedistrict varchar(3), schooldistrict varchar(3), careof varchar(30), address varchar(100), cityname varchar(100), state varchar(2), zipcode varchar(10), class varchar(10), improved varchar(1), exempt varchar(3), priced varchar(1), totalmarketvalue int4, appraisedvalue int4, taxvalue int4, landuse varchar(10), neighborhoodcode varchar(7), landvalue int4, buildingvalue int4, improvementvalue int4, appraisalarea varchar(1), postdirection varchar(2), saleprice float8, propcard varchar(150), shape_starea__ float8, shape_stlength__ float8
