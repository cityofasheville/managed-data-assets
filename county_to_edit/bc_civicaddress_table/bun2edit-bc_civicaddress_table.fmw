FME workspace bun2edit-bc_civicaddress_table.fmw

Parameters:
- DestDataset_POSTGIS = coa-gis-edit1   # Connection

Readers:
- GEODATABASE_SDE_1: GEODATABASE_SDE

Writers:
- POSTGIS_1: POSTGIS to $(DestDataset_POSTGIS)

DBO.CIVICADDRESSTBL (reader GEODATABASE_SDE_1)
    attributes: OBJECTID integer, CIVICADDRESS_ID double, LOCATION_ID double, STREET_NUMBER integer, UNIT char(4), UNIT_TYPE integer, STREET_PREFIX char(2), STREET_NAME char(30), STREET_TYPE char(4), STREET_POSTDIRECTION char(2), FULL_CIVIC_ADDRESS char(40), CREATE_DATE date, CHANGE_DATE date, USER_ID char(8), POSTAL_CODE integer, COMMCODE char(4), STREET_DUPE char(3), PINEXT char(5)
    -> coagis.bc_civicaddress_table (writer POSTGIS_1)
coagis.bc_civicaddress_table (writer POSTGIS_1)
    attributes: objectid int4, civicaddress_id float8, location_id float8, street_number int4, unit varchar(4), unit_type int4, street_prefix varchar(2), street_name varchar(30), street_type varchar(4), street_postdirection varchar(2), full_civic_address varchar(40), create_date timestamp, change_date timestamp, user_id varchar(8), postal_code int4, commcode varchar(4), street_dupe varchar(3), pinext varchar(5)
