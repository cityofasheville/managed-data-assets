FME workspace munis_to_wh-pr_employee_info.fmw

Parameters:
- SourceDataset_MSSQL_ADO_3 = munis-prod   # SQL Server Connection
- DestDataset_POSTGRES_3 = datastore1   # Connection

Readers:
- MSSQL_ADO_2: MSSQL_ADO from $(SourceDataset_MSSQL_ADO_3)

Writers:
- POSTGRES_2: POSTGRES to $(DestDataset_POSTGRES_3)

amd.pr_employee_info (reader MSSQL_ADO_2)
    attributes: emp_id integer, active varchar(1), employee varchar(67), emp_email char(50), ft_status char(2), position char(20), dept_id varchar(2), department varchar(50), div_id char(4), division varchar(50), sup_id integer, supervisor varchar(67), sup_email char(50), hire_date datetime
    -> amd.pr_employee_info (writer POSTGRES_2)
amd.pr_employee_info (writer POSTGRES_2)
    attributes: emp_id int4, active varchar(1), employee varchar(67), emp_email char(50), ft_status char(2), position char(20), dept_id varchar(2), department varchar(50), div_id char(4), division varchar(50), sup_id int4, supervisor varchar(67), sup_email char(50), hire_date timestamp
