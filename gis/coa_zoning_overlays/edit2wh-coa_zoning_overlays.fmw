FME workspace edit2wh-coa_zoning_overlays.fmw

Parameters:
- DestDataset_POSTGIS = datastore1   # Connection

Readers:
- GEODATABASE_SDE_1: GEODATABASE_SDE

Writers:
- POSTGIS_1: POSTGIS to $(DestDataset_POSTGIS)

coagis.coa_zoning_overlays (reader GEODATABASE_SDE_1)
    attributes: objectid integer, name char(100), label char(50), narrative char(150), date date, zoning_district char(50), ordinance char(50), calculated_acreage double, edit_date date, edit_by char(100), overlay_type char(150), status char(50), st_area(shape) double, st_length(shape) double
    -> amd.coa_zoning_overlays (writer POSTGIS_1)
amd.coa_zoning_overlays (writer POSTGIS_1)
    attributes: objectid int4, name varchar(100), label varchar(50), narrative varchar(150), date timestamp, zoning_district varchar(50), ordinance varchar(50), calculated_acreage float8, edit_date timestamp, edit_by varchar(100), overlay_type varchar(150), status varchar(50), st_area_shape_ float8, st_length_shape_ float8
