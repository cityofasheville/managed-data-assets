FME workspace coa_cip_project_shapes.fmw

Parameters:
- SourceDataset_POSTGIS = coa-gis-edit1b   # Connection
- SourceDataset_POSTGIS_4 = coa-gis-edit1b   # Connection
- SourceDataset_POSTGIS_6 = coa-gis-edit1b   # Connection
- DestDataset_POSTGIS_2 = mda-store-1   # Connection
- DestDataset_POSTGIS = mda-store-1   # Connection
- DestDataset_POSTGIS_3 = mda-store-1   # Connection

Readers:
- POSTGIS_1: POSTGIS from $(SourceDataset_POSTGIS)
- POSTGIS_2: POSTGIS from $(SourceDataset_POSTGIS_4) in EPSG:2264
- POSTGIS_3: POSTGIS from $(SourceDataset_POSTGIS_6) in EPSG:2264
- GEODATABASE_SDE_1: GEODATABASE_SDE
- GEODATABASE_SDE_2: GEODATABASE_SDE

Writers:
- POSTGIS_4: POSTGIS to $(DestDataset_POSTGIS_2)
- POSTGIS_5: POSTGIS to $(DestDataset_POSTGIS)
- POSTGIS_6: POSTGIS to $(DestDataset_POSTGIS_3)

coa_cip_project_multipoints (reader GEODATABASE_SDE_1)
    attributes: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
coa_cip_project_points (reader GEODATABASE_SDE_2)
    attributes: objectid integer, gis_id char(20), projecttype char(50), projectclass char(50), subclass char(50), sitetype char(20), projectname char(100), locationdescription char(256), complete char(50), edit_date char(50), edit_by char(100)
    -> coa_cip_project_points (writer POSTGIS_4)
coa_cip_project_points (writer POSTGIS_4)
    attributes: objectid int4, gis_id varchar(20), projecttype varchar(50), projectclass varchar(50), subclass varchar(50), sitetype varchar(20), projectname varchar(100), locationdescription varchar(256), complete varchar(50), edit_date varchar(50), edit_by varchar(100)
coa_cip_project_lines (reader POSTGIS_1)
    attributes: objectid int4, gis_id varchar(20), projecttype varchar(50), projectclass varchar(50), subclass varchar(50), sitetype varchar(20), projectname varchar(100), locationdescription varchar(256), complete varchar(50), gdb_geomattr_data bytea, edit_by varchar(100), edit_date varchar(50)
    -> coa_cip_project_lines (writer POSTGIS_6)
coa_cip_project_lines (writer POSTGIS_6)
    attributes: objectid int4, gis_id varchar(20), projecttype varchar(50), projectclass varchar(50), subclass varchar(50), sitetype varchar(20), projectname varchar(100), locationdescription varchar(256), complete varchar(50), gdb_geomattr_data bytea, edit_by varchar(100), edit_date varchar(50)
coa_cip_project_polygons (reader POSTGIS_2)
    attributes: objectid int4, gis_id varchar(20), projecttype varchar(50), projectclass varchar(50), subclass varchar(50), sitetype varchar(20), projectname varchar(100), locationdescription varchar(256), complete varchar(20), gdb_geomattr_data bytea, edit_by varchar(100), edit_date varchar(50)
    -> coa_cip_project_polygons (writer POSTGIS_5)
coa_cip_project_polygons (writer POSTGIS_5)
    attributes: objectid int4, gis_id varchar(20), projecttype varchar(50), projectclass varchar(50), subclass varchar(50), sitetype varchar(20), projectname varchar(100), locationdescription varchar(256), complete varchar(20), gdb_geomattr_data bytea, edit_by varchar(100), edit_date varchar(50)
