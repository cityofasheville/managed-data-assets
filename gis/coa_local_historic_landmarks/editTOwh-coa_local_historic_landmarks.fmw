FME workspace editTOwh-coa_local_historic_landmarks.fmw

Parameters:
- DestDataset_POSTGRES = mda-store-1   # Connection

Readers:
- GEODATABASE_SDE_1: GEODATABASE_SDE

Writers:
- POSTGRES_1: POSTGRES to $(DestDataset_POSTGRES)

coagis.coa_local_historic_landmarks (reader GEODATABASE_SDE_1)
    attributes: objectid integer, new_pin char(15), id_num smallint, ll_name char(50), address char(50), ordinance char(20), eff_date date, notes char(80), edit_by char(100), edit_date date
    -> public.coa_local_historic_landmarks (writer POSTGRES_1)
public.coa_local_historic_landmarks (writer POSTGRES_1)
    attributes: objectid int4, new_pin varchar(15), id_num int2, ll_name varchar(50), address varchar(50), ordinance varchar(20), eff_date timestamp, notes varchar(80), edit_by varchar(100), edit_date timestamp
