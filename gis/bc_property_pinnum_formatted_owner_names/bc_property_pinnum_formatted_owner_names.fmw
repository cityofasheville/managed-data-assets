FME workspace bc_property_pinnum_formatted_owner_names.fmw

Parameters:
- DestDataset_POSTGRES_3 = mda-store-1   # Connection

Writers:
- POSTGRES_1: POSTGRES to $(DestDataset_POSTGRES_3)

SQLCreator
    DATASET = coa-pg-db1
    EXPOSED_ATTRIBUTE_LIST = formatted_owner_name,pinnum
    SQL_STATEMENT:
      SELECT property_owner_accounts.pinnum,
        array_to_string(array_agg(property_owner_accounts.owner_name ORDER BY property_owner_accounts.accountnum ASC), ' & '::text) AS formatted_owner_name
        FROM (SELECT unnestedaccounts.pinnum, unnestedaccounts.accountnum,
                 array_to_string(array_remove(ARRAY[
                 btrim(amd.bc_property_account_master.am_last_name::text, ' '::text),
                 btrim(amd.bc_property_account_master.am_name_suffix::text, ' '::text),
                 btrim(amd.bc_property_account_master.am_first_name::text, ' '::text),
                 btrim(amd.bc_property_account_master.am_middle_name::text, ' '::text)], ''::text), ' '::text) AS owner_name
                FROM amd.bc_property_account_master,
                 (SELECT amd.bc_property.pinnum,
                         unnest(regexp_split_to_array(amd.bc_property.accountnumber::text, ';'::text)) AS accountnum
                        FROM amd.bc_property ) as unnestedaccounts
               WHERE unnestedaccounts.accountnum = amd.bc_property_account_master.am_account_no::text order by accountnum ASC) AS property_owner_accounts
       GROUP BY property_owner_accounts.pinnum
    POSTGRES_QUERY_FEATURE_TYPES_FOR_MERGE_FILTERS = Yes
    POSTGRES_SCHEMAS_FOR_TABLE_LISTING = amd
    FORMAT = POSTGRES
    POSTGRES_NAMED_CONNECTION = coa-pg-db1
    RESULT -> bc_property_pinnum_formatted_owner_names (writer POSTGRES_1)
bc_property_pinnum_formatted_owner_names (writer POSTGRES_1)
    attributes: formatted_owner_name varchar(200), pinnum varchar(200)
