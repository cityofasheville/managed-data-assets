FME workspace edit2wh-bc_property2.fmw

Parameters:
- DestDataset_POSTGIS = coa-pg-db1   # Connection

Readers:
- GEODATABASE_SDE_1: GEODATABASE_SDE in EPSG:2264

Writers:
- POSTGIS_1: POSTGIS to $(DestDataset_POSTGIS) in EPSG:2264

coagis.bc_property (reader GEODATABASE_SDE_1)
    attributes: objectid integer, pinnum char(50), pin char(15), pinext char(50), owner char(50), nmptype char(150), taxyear char(50), condounit char(50), condobuilding char(50), deedbook char(50), deedpage char(50), platbook char(50), platpage char(50), subname char(50), sublot char(50), subblock char(50), subsect char(50), updatedate char(50), housenumber char(50), numbersuffix char(50), direction char(50), streetname char(50), streettype char(50), township char(50), acreage double, accountnumber char(50), deeddate char(50), stamps double, instrument char(50), reason char(50),
      county char(50), city char(50), firedistrict char(50), schooldistrict char(50), careof char(50), address char(50), cityname char(50), state char(50), zipcode char(50), class char(50), improved char(50), exempt char(50), priced char(50), totalmarketvalue double, appraisedvalue double, taxvalue double, landuse char(50), neighborhoodcode char(50), landvalue double, buildingvalue double, improvementvalue double, appraisalarea char(50), state_route char(50), state_route_suffix char(50), propcard char(150), oldpinnum char(50), citystatezip char(50), deedurl char(254), platurl char(254), st_area(shape) double,
      st_length(shape) double
    -> amd.bc_property (writer POSTGIS_1)
amd.bc_property (writer POSTGIS_1)
    attributes: objectid int4, pinnum varchar(50), pin varchar(15), pinext varchar(50), owner varchar(50), nmptype varchar(150), taxyear varchar(50), condounit varchar(50), condobuilding varchar(50), deedbook varchar(50), deedpage varchar(50), platbook varchar(50), platpage varchar(50), subname varchar(50), sublot varchar(50), subblock varchar(50), subsect varchar(50), updatedate varchar(50), housenumber varchar(50), numbersuffix varchar(50), direction varchar(50), streetname varchar(50), streettype varchar(50), township varchar(50), acreage numeric(38,8), accountnumber varchar(50), deeddate varchar(50), stamps numeric(38,8), instrument varchar(50), reason varchar(50),
      county varchar(50), city varchar(50), firedistrict varchar(50), schooldistrict varchar(50), careof varchar(50), address varchar(50), cityname varchar(50), state varchar(50), zipcode varchar(50), class varchar(50), improved varchar(50), exempt varchar(50), priced varchar(50), totalmarketvalue numeric(38,8), appraisedvalue numeric(38,8), taxvalue numeric(38,8), landuse varchar(50), neighborhoodcode varchar(50), landvalue numeric(38,8), buildingvalue numeric(38,8), improvementvalue numeric(38,8), appraisalarea varchar(50), state_route varchar(50), state_route_suffix varchar(50), propcard varchar(150), oldpinnum varchar(50), citystatezip varchar(50), deedurl varchar(254), platurl varchar(254), gdb_geomattr_data bytea
