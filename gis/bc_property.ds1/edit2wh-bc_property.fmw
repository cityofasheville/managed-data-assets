FME workspace edit2wh-bc_property.fmw

Readers:
- GEODATABASE_SDE_1: GEODATABASE_SDE in EPSG:2264

Writers:
- GEODATABASE_SDE_3: GEODATABASE_SDE to <Unused>

coagis.bc_property (reader GEODATABASE_SDE_1)
    attributes: objectid integer, pinnum char(50), pin char(15), pinext char(50), owner char(50), nmptype char(150), taxyear char(50), condounit char(50), condobuilding char(50), deedbook char(50), deedpage char(50), platbook char(50), platpage char(50), subname char(50), sublot char(50), subblock char(50), subsect char(50), updatedate char(50), housenumber char(50), numbersuffix char(50), direction char(50), streetname char(50), streettype char(50), township char(50), acreage double, accountnumber char(50), deeddate char(50), stamps double, instrument char(50), reason char(50),
      county char(50), city char(50), firedistrict char(50), schooldistrict char(50), careof char(50), address char(50), cityname char(50), state char(50), zipcode char(50), class char(50), improved char(50), exempt char(50), priced char(50), totalmarketvalue double, appraisedvalue double, taxvalue double, landuse char(50), neighborhoodcode char(50), landvalue double, buildingvalue double, improvementvalue double, appraisalarea char(50), state_route char(50), state_route_suffix char(50), propcard char(150), oldpinnum char(50), citystatezip char(50), deedurl char(254), platurl char(254), st_area(shape) double,
      st_length(shape) double
    -> amd.bc_property (writer GEODATABASE_SDE_3)
amd.bc_property (writer GEODATABASE_SDE_3)
    attributes: objectid integer, pinnum char(50), pin char(15), pinext char(50), owner char(50), nmptype char(150), taxyear char(50), condounit char(50), condobuilding char(50), deedbook char(50), deedpage char(50), platbook char(50), platpage char(50), subname char(50), sublot char(50), subblock char(50), subsect char(50), updatedate char(50), housenumber char(50), numbersuffix char(50), direction char(50), streetname char(50), streettype char(50), township char(50), acreage double, accountnumber char(50), deeddate char(50), stamps double, instrument char(50), reason char(50),
      county char(50), city char(50), firedistrict char(50), schooldistrict char(50), careof char(50), address char(50), cityname char(50), state char(50), zipcode char(50), class char(50), improved char(50), exempt char(50), priced char(50), totalmarketvalue double, appraisedvalue double, taxvalue double, landuse char(50), neighborhoodcode char(50), landvalue double, buildingvalue double, improvementvalue double, appraisalarea char(50), state_route char(50), state_route_suffix char(50), propcard char(150), oldpinnum char(50), citystatezip char(50), deedurl char(254), platurl char(254), st_area(shape) double,
      st_length(shape) double
