FME workspace edit2wh-coa_national_register_properties.fmw

Readers:
- GEODATABASE_SDE_1: GEODATABASE_SDE

Writers:
- GEODATABASE_SDE_2: GEODATABASE_SDE to <Unused>

coagis.coa_national_register_properties (reader GEODATABASE_SDE_1)
    attributes: objectid integer, id integer, name char(50), area_type char(20), edit_date date, edit_by char(100), st_area(shape) double, st_length(shape) double, nr_pdfs char(100)
    -> amd.coa_national_register_properties (writer GEODATABASE_SDE_2)
amd.coa_national_register_properties (writer GEODATABASE_SDE_2)
    attributes: objectid integer, id integer, name char(50), area_type char(20), edit_date date, edit_by char(100), st_area_shape_ double, st_length_shape_ double, nr_pdfs char(100)
