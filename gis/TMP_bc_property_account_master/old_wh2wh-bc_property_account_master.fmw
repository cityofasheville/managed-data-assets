FME workspace old_wh2wh-bc_property_account_master.fmw

Parameters:
- SourceDataset_POSTGRES = coa-gis-warehouse1   # Connection
- DestDataset_POSTGRES = coa-pg-db1-datastore1   # Connection

Readers:
- POSTGRES_1: POSTGRES from $(SourceDataset_POSTGRES)

Writers:
- POSTGRES_2: POSTGRES to $(DestDataset_POSTGRES)

coagis.bc_property_account_master (reader POSTGRES_1)
    attributes: am_account_no int4, am_owner_type varchar(3), am_last_name varchar(80), am_first_name varchar(35), am_middle_name varchar(35), am_name_suffix varchar(5), am_address1 varchar(35), am_address2 varchar(35), am_address3 varchar(50), am_city varchar(20), am_state varchar(2), am_zip varchar(5), am_zip_plus4 varchar(4), am_foreign_address_flag varchar(1), am_foreign_country varchar(20), am_foreign_zip varchar(10), am_exempt_account_flag varchar(1), am_bad_address_flag varchar(1), am_bypass_postal_flag varchar(1), am_last_update_date timestamp, am_last_update_user varchar(3), pkam_account_no int4,PRIKEY
    -> amd.bc_property_account_master (writer POSTGRES_2)
amd.bc_property_account_master (writer POSTGRES_2)
    attributes: am_account_no int4, am_owner_type varchar(3), am_last_name varchar(80), am_first_name varchar(35), am_middle_name varchar(35), am_name_suffix varchar(5), am_address1 varchar(35), am_address2 varchar(35), am_address3 varchar(50), am_city varchar(20), am_state varchar(2), am_zip varchar(5), am_zip_plus4 varchar(4), am_foreign_address_flag varchar(1), am_foreign_country varchar(20), am_foreign_zip varchar(10), am_exempt_account_flag varchar(1), am_bad_address_flag varchar(1), am_bypass_postal_flag varchar(1), am_last_update_date timestamp, am_last_update_user varchar(3), pkam_account_no int4,PRIKEY
