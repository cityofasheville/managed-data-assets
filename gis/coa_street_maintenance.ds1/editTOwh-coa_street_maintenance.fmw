FME workspace editTOwh-coa_street_maintenance.fmw

Parameters:
- DestDataset_POSTGIS_3 = mda-store-1   # Connection

Readers:
- GEODATABASE_SDE_1: GEODATABASE_SDE

Writers:
- POSTGIS_1: POSTGIS to $(DestDataset_POSTGIS_3)

coa_street_maintenance (reader GEODATABASE_SDE_1)
    attributes: objectid integer, centerline_id char(20), full_street_name char(50), maintenance_entity char(30), furtherinfo char(150), frommeasure double, tomeasure double, edit_date date, edit_by char(100), st_length(shape) double
    -> coa_street_maintenance (writer POSTGIS_1)
coa_street_maintenance (writer POSTGIS_1)
    attributes: objectid int4, centerline_id varchar(20), full_street_name varchar(50), maintenance_entity varchar(30), furtherinfo varchar(150), frommeasure float8, tomeasure float8, edit_date timestamp, edit_by varchar(100), st_length_shape_ float8
