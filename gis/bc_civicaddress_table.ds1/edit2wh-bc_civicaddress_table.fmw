FME workspace edit2wh-bc_civicaddress_table.fmw

Readers:
- GEODATABASE_SDE_1: GEODATABASE_SDE in EPSG:2264

Writers:
- GEODATABASE_SDE_2: GEODATABASE_SDE in EPSG:2264

coagis.bc_civicaddress_table (reader GEODATABASE_SDE_1)
    attributes: objectid integer, civicaddress_id double, location_id double, street_number integer, unit char(4), unit_type integer, street_prefix char(2), street_name char(30), street_type char(4), street_postdirection char(2), full_civic_address char(40), create_date date, change_date date, user_id char(8), postal_code integer, commcode char(4), street_dupe char(3), pinext char(5)
    -> amd.bc_civicaddress_table (writer GEODATABASE_SDE_2)
amd.bc_civicaddress_table (writer GEODATABASE_SDE_2)
    attributes: objectid integer, civicaddress_id double, location_id double, street_number integer, unit char(4), unit_type integer, street_prefix char(2), street_name char(30), street_type char(4), street_postdirection char(2), full_civic_address char(40), create_date date, change_date date, user_id char(8), postal_code integer, commcode char(4), street_dupe char(3), pinext char(5)
