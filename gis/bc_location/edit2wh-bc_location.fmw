FME workspace edit2wh-bc_location.fmw

Parameters:
- SourceDataset_POSTGIS = coa-gis-edit1   # Connection
- DestDataset_POSTGIS = coa-pg-db1-datastore1   # Connection

Readers:
- POSTGIS_1: POSTGIS from $(SourceDataset_POSTGIS)

Writers:
- POSTGIS_2: POSTGIS to $(DestDataset_POSTGIS)

bc_location (reader POSTGIS_1)
    attributes: objectid int4, location_id float8, locationtype int4, civicaddress_id float8, parent_location_id float8, building_id float8, centerline_id float8, user_id varchar(8), esn int2, x_coord float8, y_coord float8, commcode varchar(4), primary_structure int2, create_date timestamp, change_date timestamp, parcel_id varchar(10), gdb_geomattr_data bytea
    -> amd.bc_location (writer POSTGIS_2)
amd.bc_location (writer POSTGIS_2)
    attributes: objectid int4, location_id float8, locationtype int4, civicaddress_id float8, parent_location_id float8, building_id float8, centerline_id float8, user_id varchar(8), esn int2, x_coord float8, y_coord float8, commcode varchar(4), primary_structure int2, create_date timestamp, change_date timestamp, parcel_id varchar(10), gdb_geomattr_data bytea
