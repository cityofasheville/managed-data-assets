FME workspace edit2wh-coa_zip_code2.fmw

Parameters:
- DestDataset_POSTGIS = coa-pg-db1   # Connection

Readers:
- GEODATABASE_SDE_1: GEODATABASE_SDE in EPSG:2264

Writers:
- POSTGIS_1: POSTGIS to $(DestDataset_POSTGIS) in EPSG:2264

coagis.coa_zip_code (reader GEODATABASE_SDE_1)
    attributes: objectid integer, bc_zipcode integer, bc_zipco_1 integer, zip char(5), po_name char(28), state char(2), sumblkpop integer, pop2000 integer, citycode char(4), edit_date date, edit_by char(100), st_area(shape) double, st_length(shape) double
    -> amd.coa_zip_code (writer POSTGIS_1)
amd.coa_zip_code (writer POSTGIS_1)
    attributes: objectid int4, bc_zipcode int4, bc_zipco_1 int4, zip varchar(5), po_name varchar(28), state varchar(2), sumblkpop int4, pop2000 int4, citycode varchar(4), edit_date timestamp, edit_by varchar(100), gdb_geomattr_data bytea
