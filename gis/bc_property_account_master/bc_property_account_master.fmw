FME workspace bc_property_account_master.fmw

Parameters:
- SourceDataset_MSSQL_ADO = @itsqlprod.bcdomain.local/pinhistory   # SQL Server Connection
- DestDataset_POSTGRES = mda-store-1   # Connection

Readers:
- MSSQL_ADO_1: MSSQL_ADO from $(SourceDataset_MSSQL_ADO)

Writers:
- POSTGRES_1: POSTGRES to $(DestDataset_POSTGRES)

SQLCreator
    EXPOSED_ATTRIBUTE_LIST = AM_account_no,AM-address1,AM-address2,AM-address3,AM-bad-address-flag,AM-bypass-postal-flag,AM-city,AM-exempt-account-flag,AM-first-name,AM-foreign-address_flag,AM-foreign-country,AM-foreign-zip,AM-last-name,AM-last-update-date,AM-last-update-user,AM-middle-name,AM-name-suffix,AM-owner-type,AM-state,AM-zip,AM-zip-plus4,pkAM_account_no
    MSSQL_ADO_NAMED_CONNECTION = @itsqlprod.bcdomain.local/pinhistory
    MSSQL_ADO_COMMAND_TIMEOUT = 30
    MSSQL_ADO_QUERY_FEATURE_TYPES_FOR_MERGE_FILTERS = Yes
    DATASET = @itsqlprod.bcdomain.local/pinhistory
    SQL_STATEMENT = select * from amaccountmaster
    FORMAT = MSSQL_ADO
    RESULT -> bc_property_account_master (writer POSTGRES_1)
bc_property_account_master (writer POSTGRES_1)
    attributes: am_account_no varchar(200), am_address1 varchar(200), am_address2 varchar(200), am_address3 varchar(200), am_bad_address_flag varchar(200), am_bypass_postal_flag varchar(200), am_city varchar(200), am_exempt_account_flag varchar(200), am_first_name varchar(200), am_foreign_address_flag varchar(200), am_foreign_country varchar(200), am_foreign_zip varchar(200), am_last_name varchar(200), am_last_update_date varchar(200), am_last_update_user varchar(200), am_middle_name varchar(200), am_name_suffix varchar(200), am_owner_type varchar(200), am_state varchar(200), am_zip varchar(200), am_zip_plus4 varchar(200), pkam_account_no varchar(200)
