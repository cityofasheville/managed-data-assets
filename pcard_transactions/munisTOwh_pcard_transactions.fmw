FME workspace munisTOwh_pcard_transactions.fmw

Parameters:
- SourceDataset_MSSQL_ADO_3 = munis-prod   # SQL Server Connection
- DestDataset_POSTGRES_3 = mda-store-1   # Connection

Readers:
- MSSQL_ADO_1: MSSQL_ADO from $(SourceDataset_MSSQL_ADO_3)

Writers:
- POSTGRES_2: POSTGRES to $(DestDataset_POSTGRES_3)

amd.pcard_transaction (reader MSSQL_ADO_1)
    attributes: dept_id varchar(2), department varchar(50), div_id varchar(4), division varchar(50), cardholder char(50), statement_id integer, charge_date date, amount numeric(13,2), vendor_id integer, vendor_name varchar(50), description char(100), receipt varchar(1)
    -> internal.pcard_transaction (writer POSTGRES_2)
internal.pcard_transaction (writer POSTGRES_2)
    attributes: dept_id varchar(2), department varchar(50), div_id varchar(4), division varchar(50), cardholder char(50), statement_id int4, charge_date date, amount numeric(13,2), vendor_id int4, vendor_name varchar(50), description char(100), receipt varchar(1)
