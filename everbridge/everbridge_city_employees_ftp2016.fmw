FME workspace everbridge_city_employees_ftp2016.fmw

Parameters:
- SourceDataset_MSSQL_ADO = munprod   # SQL Server Connection

Readers:
- MSSQL_ADO_1: MSSQL_ADO from $(SourceDataset_MSSQL_ADO)

avl.PR_City_Employees_Everbridge (reader MSSQL_ADO_1)
    attributes: Test varchar(4)
    -> FeatureWriter [avl.PR_City_Employees_Everbridge]
FeatureWriter
    DATASET = C:\COA\managed-data-assets\everbridge
    CSV_SEPARATOR = ,
    WRITER_DIRECTIVES = SEPARATOR,,,QUOTE_OUTPUT,if_needed,DESTINATION_DATASETTYPE_VALIDATION,Yes,WRITE_SCHEMA_FILE,no,APPEND,No,QUOTE_FIELD_NAMES,no,EXTENSION,csv,FIELD_NAMES,yes,WRITE_UTF8_BOM,yes
    CSV_DESTINATION_DATASETTYPE_VALIDATION = Yes
    CSV_WRITE_SCHEMA_FILE = no
    CSV_QUOTE_OUTPUT = if_needed
    FORMAT = CSV
    CSV_QUOTE_FIELD_NAMES = no
    CSV_APPEND = No
    CSV_WRITE_UTF8_BOM = yes
    DATASET_ATTR = _dataset
    CSV_FIELD_NAMES = yes
    FEATURE_TYPE_LIST_ATTR = _feature_type
    TOTAL_FEATURES_WRITTEN_ATTR = _total_features_written
    CSV_EXTENSION = csv
