FME workspace everbridge_water_customers_ftp.fmw

Parameters:
- SourceDataset_MSSQL_ADO = munprod   # SQL Server Connection

Readers:
- MSSQL_ADO_1: MSSQL_ADO from $(SourceDataset_MSSQL_ADO)

avl.UB_Water_Customers_Everbridge (reader MSSQL_ADO_1)
    attributes: First Name varchar(64), Last Name varchar(38), External ID varchar(37), Record Type varchar(14), Groups varchar(19), Location 1 varchar(22), Extension Phone 1 varchar(12), Email Address 1 varchar(254), Apt/Suite/Unit 1 varchar(5), Street Address 1 varchar(59), City 1 char(4), State/Province 1 char(2), Postal Code 1 char(10)
    -> FeatureWriter [avl.UB_Water_Customers_Everbridge]
FeatureWriter
    CSV2_DELIMITER = ,
    CSV2_WRITE_SCHEMA_FILE = NO
    CSV2_COORDINATE_SYSTEM_GRANULARITY = FEATURE_TYPE
    TOTAL_FEATURES_WRITTEN_ATTR = _total_features_written
    CSV2_ROW_TERMINATION = System
    CSV2_QUALIFY_FIELD_NAMES = if_needed
    CSV2_FIELD_QUALIFIER_ESCAPE_CHARACTER = "
    DATASET = C:\coa\managed-data-assets\everbridge
    CSV2_QUALIFY_FIELD_VALUES = if_needed
    CSV2_EXTENSION = csv
    CSV2_WRITE_FIELD_NAMES = firstrow
    CSV2_FIELD_QUALIFIER_CHARACTER = "
    FEATURE_TYPE_LIST_ATTR = _feature_type
    DATASET_ATTR = _dataset
    FORMAT = CSV2
    CSV2_EXISTING_FILE_HANDLING = Yes
    CSV2_WRITE_BOM_FOR_UNICODE = Yes
