FME workspace everbridge_water_customers_ftp2016.fmw

Parameters:
- SourceDataset_MSSQL_ADO = munprod   # SQL Server Connection

Readers:
- MSSQL_ADO_1: MSSQL_ADO from $(SourceDataset_MSSQL_ADO)

avl.UB_Water_Customers_Everbridge (reader MSSQL_ADO_1)
    attributes: First Name varchar(64), Last Name varchar(38), External ID varchar(37), Record Type varchar(14), Groups varchar(19), Location 1 varchar(22), Extension Phone 1 varchar(12), Email Address 1 varchar(254), Apt/Suite/Unit 1 varchar(5), Street Address 1 varchar(59), City 1 char(4), State/Province 1 char(2), Postal Code 1 char(10)
    -> FeatureWriter [avl.UB_Water_Customers_Everbridge]
FeatureWriter
    WRITER_DIRECTIVES = APPEND,No,WRITE_SCHEMA_FILE,no,QUOTE_OUTPUT,if_needed,EXTENSION,csv,QUOTE_FIELD_NAMES,no,SEPARATOR,,,DESTINATION_DATASETTYPE_VALIDATION,Yes,WRITE_UTF8_BOM,yes,FIELD_NAMES,yes
    CSV_APPEND = No
    TOTAL_FEATURES_WRITTEN_ATTR = _total_features_written
    FEATURE_TYPE_LIST_ATTR = _feature_type
    CSV_DESTINATION_DATASETTYPE_VALIDATION = Yes
    CSV_QUOTE_FIELD_NAMES = no
    CSV_SEPARATOR = ,
    CSV_FIELD_NAMES = yes
    CSV_WRITE_SCHEMA_FILE = no
    DATASET_ATTR = _dataset
    DATASET = C:\COA\managed-data-assets\everbridge
    CSV_WRITE_UTF8_BOM = yes
    FORMAT = CSV
    CSV_QUOTE_OUTPUT = if_needed
    CSV_EXTENSION = csv
