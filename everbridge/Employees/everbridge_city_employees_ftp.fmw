FME workspace everbridge_city_employees_ftp.fmw

Parameters:
- SourceDataset_MSSQL_ADO_3 = munprod   # SQL Server Connection

Readers:
- MSSQL_ADO_1: MSSQL_ADO from $(SourceDataset_MSSQL_ADO_3)

avl.PR_City_Employees_Everbridge (reader MSSQL_ADO_1)
    attributes: Test varchar(4)
    -> FeatureWriter [avl.PR_City_Employees_Everbridge]
FeatureWriter
    CSV2_WRITE_BOM_FOR_UNICODE = Yes
    CSV2_COORDINATE_SYSTEM_GRANULARITY = FEATURE_TYPE
    CSV2_WRITE_FIELD_NAMES = firstrow
    CSV2_WRITE_SCHEMA_FILE = NO
    CSV2_EXTENSION = csv
    CSV2_EXISTING_FILE_HANDLING = Yes
    CSV2_FIELD_QUALIFIER_CHARACTER = "
    FEATURE_TYPE_LIST_ATTR = _feature_type
    CSV2_DELIMITER = ,
    DATASET_ATTR = _dataset
    DATASET = .
    CSV2_QUALIFY_FIELD_VALUES = if_needed
    CSV2_ROW_TERMINATION = System
    CSV2_QUALIFY_FIELD_NAMES = if_needed
    FORMAT = CSV2
    TOTAL_FEATURES_WRITTEN_ATTR = _total_features_written
    CSV2_FIELD_QUALIFIER_ESCAPE_CHARACTER = "
