FME workspace editTOwh-bc_street.fmw

Parameters:
- SourceDataset_POSTGIS = coa-gis-edit1b   # Connection
- DestDataset_POSTGIS = mda-store-1   # Connection

Readers:
- POSTGIS_1: POSTGIS from $(SourceDataset_POSTGIS)

Writers:
- POSTGIS_2: POSTGIS to $(DestDataset_POSTGIS)

bc_street (reader POSTGIS_1)
    attributes: objectid int4,PRIKEY, centerline_id numeric(38,8), road_class int4, street_prefix varchar(2), street_name varchar(30), street_type varchar(4), street_postdirection varchar(2), street_dupe varchar(1), full_street_name varchar(32), speed_limit int4, lane_count int4, left_from_address int4, left_to_address int4, right_from_address int4, right_to_address int4, user_id varchar(8), create_date timestamp, change_date timestamp, lesn int2, resn int2, lzip int4, rzip int4, lcommcode varchar(4), rcommcode varchar(4), route_id varchar(20), maximo_type varchar(30), maximo_seq_num int4, asset_code varchar(50), mrc varchar(8), min_range int4,
      max_range int4
    -> MeasureRemover
MeasureRemover
    REMOVE_ALL = Yes
    -> bc_street (writer POSTGIS_2)
bc_street (writer POSTGIS_2)
    attributes: objectid int4, centerline_id numeric(38,8), road_class int4, street_prefix varchar(2), street_name varchar(30), street_type varchar(4), street_postdirection varchar(2), street_dupe varchar(1), full_street_name varchar(32), speed_limit int4, lane_count int4, left_from_address int4, left_to_address int4, right_from_address int4, right_to_address int4, user_id varchar(8), create_date timestamp, change_date timestamp, lesn int2, resn int2, lzip int4, rzip int4, lcommcode varchar(4), rcommcode varchar(4), route_id varchar(20), maximo_type varchar(30), maximo_seq_num int4, asset_code varchar(50), mrc varchar(8), min_range int4,
      max_range int4
