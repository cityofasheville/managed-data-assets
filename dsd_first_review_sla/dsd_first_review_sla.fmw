FME workspace dsd_first_review_sla.fmw

Parameters:
- SourceDataset_MSSQL_ADO = @coa-dscdb/accelaprod   # SQL Server Connection
- DestDataset_POSTGRES_3 = mda-store-1   # Connection

Readers:
- MSSQL_ADO_1: MSSQL_ADO from $(SourceDataset_MSSQL_ADO)

Writers:
- POSTGRES_2: POSTGRES to $(DestDataset_POSTGRES_3)

amd.dsd_first_review_sla (reader MSSQL_ADO_1)
    attributes: record_id varchar(30), first_date bigint, record_type varchar(255), group varchar(30), type varchar(30), sub_type varchar(30), category varchar(30), task varchar(100), task_status varchar(200), sla_desc varchar(4000), start varchar(30), sla numeric(28,1), due varchar(30), first_plan_reviewed_date varchar(30), month integer, year integer, met_sla varchar(1), sla_business integer, worked_days_business integer
    -> internal.dsd_first_review_sla (writer POSTGRES_2)
internal.dsd_first_review_sla (writer POSTGRES_2)
    attributes: record_id varchar(30), first_date int8, record_type varchar(255), group varchar(30), type varchar(30), sub_type varchar(30), category varchar(30), task varchar(100), task_status varchar(200), sla_desc varchar(4000), start varchar(30), sla numeric(28,1), due varchar(30), first_plan_reviewed_date varchar(30), month int4, year int4, met_sla varchar(1), sla_business int4, worked_days_business int4
