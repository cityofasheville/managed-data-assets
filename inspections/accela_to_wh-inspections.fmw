FME workspace accela_to_wh-inspections.fmw

Parameters:
- SourceDataset_MSSQL_ADO = @coa-dscdb/accelaprod   # SQL Server Connection
- DestDataset_POSTGRES = mda-store-1   # Connection

Readers:
- MSSQL_ADO_1: MSSQL_ADO from $(SourceDataset_MSSQL_ADO)

Writers:
- POSTGRES_1: POSTGRES to $(DestDataset_POSTGRES)

amd.inspections (reader MSSQL_ADO_1)
    attributes: inspection_id bigint, permit_num varchar(30), permit_group varchar(30), permit_type varchar(30), permit_subtype varchar(30), permit_category varchar(30), inspection_type varchar(255), requestor_name varchar(212), status varchar(30), inspector varchar(141), request_date datetime, scheduled_date datetime, completed_date datetime, submit_date datetime, result_comment varchar(8000), unit_number varchar(20), record_date datetime, internal_record_id varchar(17)
    -> internal.inspections (writer POSTGRES_1)
internal.inspections (writer POSTGRES_1)
    attributes: inspection_id int8, permit_num varchar(30), permit_group varchar(30), permit_type varchar(30), permit_subtype varchar(30), permit_category varchar(30), inspection_type varchar(255), requestor_name varchar(212), status varchar(30), inspector varchar(141), request_date timestamp, scheduled_date timestamp, completed_date timestamp, submit_date timestamp, result_comment varchar(8000), unit_number varchar(20), record_date timestamp, internal_record_id varchar(17)
