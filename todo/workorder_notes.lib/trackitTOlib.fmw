FME workspace trackitTOlib.fmw

Parameters:
- DestDataset_POSTGRES = library_playground   # Connection

Writers:
- POSTGRES_1: POSTGRES to $(DestDataset_POSTGRES)

SQLCreator
    SQL_STATEMENT:
      SELECT TaskNoteId AS id, TaskNote.woid AS workorder_id, CreateDate create_time, ModifiedDate last_edit_time,
      TaskNoteTypeName type, TaskNoteCategoryDescr subtype,
      CreatedBy author, NoteText AS note
      FROM dbo.TASKS
      INNER JOIN dbo.TaskNote
      ON TASKS.WO_NUM = TaskNote.woid
      LEFT JOIN dbo.TaskNoteCategory
      ON TaskNote.TaskNoteCategoryId = TaskNoteCategory.TaskNoteCategoryId
      LEFT JOIN dbo.TaskNoteType
      ON TaskNote.TaskNoteTypeId = TaskNoteType.TaskNoteTypeId
      WHERE  DATEDIFF(DAY, TASKS.REQDATE, GETDATE()) <= 365
      ORDER BY CreateDate DESC
    MSSQL_ADO_QUERY_FEATURE_TYPES_FOR_MERGE_FILTERS = Yes
    FORMAT = MSSQL_ADO
    MSSQL_ADO_NAMED_CONNECTION = TrackIT
    EXPOSED_ATTRIBUTE_LIST = id,workorder_id,create_time,last_edit_time,type,subtype,author,note
    DATASET = TrackIT
    MSSQL_ADO_COMMAND_TIMEOUT = 30
    RESULT -> r_it.workorder_notes (writer POSTGRES_1)
r_it.workorder_notes (writer POSTGRES_1)
    attributes: id varchar(200), workorder_id varchar(200), create_time varchar(200), last_edit_time varchar(200), type varchar(200), subtype varchar(200), author varchar(200), note varchar(200)
