FME workspace accelaTOmdastore1_buncombe_tax_permits.fmw

Parameters:
- SourceDataset_MSSQL_ADO = @coa-dscdb/accelaprod   # SQL Server Connection
- DestDataset_POSTGRES = mda-store-1   # Connection

Readers:
- MSSQL_ADO_1: MSSQL_ADO from $(SourceDataset_MSSQL_ADO)

Writers:
- POSTGRES_1: POSTGRES to $(DestDataset_POSTGRES)

dbo.BUNCOMBE_TAX_PERMITS (reader MSSQL_ADO_1)
    attributes: permit_num varchar(30), parcel_num varchar(24), issue_date date, status_date date, permit_type varchar(50), description varchar(100), total_cost money, permit_status varchar(30), directions varchar(100), tax_year smallint, lot varchar(40), subdivision varchar(240), total_sf varchar(10), basement_heated_sf varchar(10), basement_unheated_sf varchar(10), garage_carport_sf varchar(10), total_heated_sf varchar(10), foundation varchar(30), units varchar(10), stories numeric(6,2), bedrooms varchar(10), type_of_heat varchar(30), mh_year varchar(100), mh_size varchar(10), quantity varchar(10), basement_finished varchar(1), bathrooms varchar(10), note varchar(4000), employee varchar(30), active_flag varchar(1)
    -> buncombe_tax_permits (writer POSTGRES_1)
buncombe_tax_permits (writer POSTGRES_1)
    attributes: permit_num varchar(30), parcel_num varchar(24), issue_date date, status_date date, permit_type varchar(50), description varchar(100), total_cost float8, permit_status varchar(30), directions varchar(100), tax_year int2, lot varchar(40), subdivision varchar(240), total_sf varchar(10), basement_heated_sf varchar(10), basement_unheated_sf varchar(10), garage_carport_sf varchar(10), total_heated_sf varchar(10), foundation varchar(30), units varchar(10), stories numeric(6,2), bedrooms varchar(10), type_of_heat varchar(30), mh_year varchar(100), mh_size varchar(10), quantity varchar(10), basement_finished varchar(1), bathrooms varchar(10), note varchar(4000), employee varchar(30), active_flag varchar(1)
