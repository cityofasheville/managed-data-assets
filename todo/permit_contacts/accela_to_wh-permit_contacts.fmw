FME workspace accela_to_wh-permit_contacts.fmw

Parameters:
- SourceDataset_MSSQL_ADO = Accela Prodution Environment   # SQL Server Connection
- DestDataset_POSTGRES = mda-store-1   # Connection

Readers:
- MSSQL_ADO_1: MSSQL_ADO from $(SourceDataset_MSSQL_ADO)

Writers:
- POSTGRES_1: POSTGRES to $(DestDataset_POSTGRES)

amd.permit_contacts (reader MSSQL_ADO_1)
    attributes: permit_num varchar(30), contact_type varchar(255), contact_name varchar(141), contact_business_name varchar(255), contact_address1 varchar(200), contact_address2 varchar(200), contact_city varchar(30), contact_state varchar(30), contact_zip varchar(10), contact_phone varchar(40)
    -> internal.permit_contacts (writer POSTGRES_1)
internal.permit_contacts (writer POSTGRES_1)
    attributes: permit_num varchar(30), contact_type varchar(255), contact_name varchar(141), contact_business_name varchar(255), contact_address1 varchar(200), contact_address2 varchar(200), contact_city varchar(30), contact_state varchar(30), contact_zip varchar(10), contact_phone varchar(40)
