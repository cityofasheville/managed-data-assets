FME workspace MunisTOwh-utility_work_orders.fmw

Parameters:
- SourceDataset_MSSQL_ADO = munprod   # SQL Server Connection
- DestDataset_POSTGRES = coa-gis-warehouse1   # Connection
- DestDataset_POSTGRES_3 = coa-gis-warehouse1   # Connection

Readers:
- MSSQL_ADO_1: MSSQL_ADO from $(SourceDataset_MSSQL_ADO)

Writers:
- POSTGRES_1: POSTGRES to $(DestDataset_POSTGRES)
- POSTGRES_2: POSTGRES to $(DestDataset_POSTGRES_3)

avl.ut_workorders_gis_import (reader MSSQL_ADO_1)
    attributes: utwo_wo_num integer, utwo_code char(4), utwo_comment1 char(60), utwo_type char(4), utwo_ent_date datetime, utwo_status char(1), utwo_account char(30), utwo_comment2 char(60), utwo_comment3 char(60), utwo_comment4 char(60), utwo_complt_by char(3), utwo_reas_compl char(4), spms_long char(30), utwo_dept char(5), spms_code char(4), spms_type char(4), spms_short char(10), utwo_complt_date datetime, utwo_assign_to char(4), utwo_sched_time char(5), utwo_seq smallint, utwo_priority char(2), utwo_request_dt datetime, utwo_complt_beg char(5), utacm_account char(30), utacm_loc_no integer, utacm_loc_street char(25), utacm_loc_str_typ char(10), utacm_parcel char(30), utacm_loc_apt char(5),
      utacm_loc_post_dir char(4), utacm_loc_pre_dir char(4)
    -> Counter
Counter
    START = 0
    CNT_ATTR = _count
    SCOPE = Global
    DOMAIN = counter
    -> munis_utility_billing_wok_orders_table (writer POSTGRES_2)
munis_utility_billing_wok_orders_table (writer POSTGRES_2)
    attributes: utwo_wo_num int4, utwo_code varchar(4), utwo_comment1 varchar(60), utwo_type varchar(4), utwo_ent_date timestamp, utwo_status varchar(1), utwo_account varchar(30), utwo_comment2 varchar(60), utwo_comment3 varchar(60), utwo_comment4 varchar(60), utwo_complt_by varchar(3), utwo_reas_compl varchar(4), spms_long varchar(30), utwo_dept varchar(5), spms_code varchar(4), spms_type varchar(4), spms_short varchar(10), utwo_complt_date timestamp, utwo_assign_to varchar(4), utwo_sched_time varchar(5), utwo_seq int2, utwo_priority varchar(2), utwo_request_dt timestamp, utwo_complt_beg varchar(5), utacm_account varchar(30), utacm_loc_no int4, utacm_loc_street varchar(25), utacm_loc_str_typ varchar(10), utacm_parcel varchar(30), utacm_loc_apt varchar(5),
      utacm_loc_post_dir varchar(4), utacm_loc_pre_dir varchar(4), pid varchar(200),PrimaryKey
