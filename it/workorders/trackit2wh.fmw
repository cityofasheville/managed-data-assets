FME workspace trackit2wh.fmw

Parameters:
- SourceDataset_MSSQL_ADO = TrackIT   # SQL Server Connection
- DestDataset_POSTGRES = coa-pg-db1   # Connection

Readers:
- MSSQL_ADO_1: MSSQL_ADO from $(SourceDataset_MSSQL_ADO)

Writers:
- POSTGRES_1: POSTGRES to $(DestDataset_POSTGRES)

dbo.TASKS (reader MSSQL_ADO_1)
    attributes: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
SQLCreator
    FORMAT = MSSQL_ADO
    DATASET = TrackIT
    SQL_STATEMENT:
      SELECT   A.WOID AS ID, A.PARENTWOID AS ParentID, A.RESPONSEDATE AS RespondBy,
      				  A.TASK AS Summary, A.TYPE AS Type, A.REQUEST AS Requestor,
      				  A.REQDATE AS RequestedDate, A.CLSDDATE AS ResolutionDate,
      				  A.ELAPSETIME AS ElapsedTime, A.PRIORITY AS Priority,
      				  A.DUEDATE AS DueDate, A.RESPONS AS AssignedTechnician, A.COMPLETED AS DateCompleted, A.HOURS AS Hours,
      				  A.DEPT AS Department, A.DESCRIPT AS Notes, A.NOTE AS Resolution,
      				  Status.WorkOrderStatusName AS CurrentStatus,
      				  A.LOOKUP1 AS IncidentOrServiceReq, A.LOOKUP2 AS HotList,
      				  A.RESPONDEDDATE AS DateResponded, Type.WorkOrderTypeName,
      				  A.WOTYPE2 AS Subtype,
      				  A.WO_TEXT1 AS Text1,
      				  A.WO_TEXT4 AS Text4,
      				  A.TaskLookup3 AS ForwardProject, A.TaskLookup4 AS OrgImpact,
      				  A.TaskLookup5 AS RequestorPriority, A.TaskLookup6, A.TaskLookup7,
      				  A.TaskLookup8 AS ITInvolvement,
      				  A.ASSNDATE, A.WOTYPE3, A.STATUS,
      				  A.WO_TEXT2, A.WO_TEXT3, A.WO_TEXT5, A.WO_TEXT6,
      				  A.WO_NUM1, A.WO_INT1
      FROM [TRACKIT_DATA_PROD].[dbo].[TASKS] AS A
      LEFT JOIN WorkOrderStatus AS Status ON A.WorkOrderStatusId = Status.WorkOrderStatusId
      left join WorkOrderType AS Type ON A.WorkOrderTypeId = Type.WorkOrderTypeId
      order by A.ASSNDATE Desc
    MSSQL_ADO_COMMAND_TIMEOUT = 30
    EXPOSED_ATTRIBUTE_LIST = AssignedTechnician,ASSNDATE,CurrentStatus,DateCompleted,DateResponded,Department,DueDate,ElapsedTime,ForwardProject,HotList,Hours,ID,IncidentOrServiceReq,ITInvolvement,Notes,OrgImpact,ParentID,Priority,RequestedDate,Requestor,RequestorPriority,Resolution,ResolutionDate,RespondBy,STATUS,Subtype,Summary,TaskLookup6,TaskLookup7,Text1,Text4,Type,WO_INT1,WO_NUM1,WO_TEXT2,WO_TEXT3,WO_TEXT5,WO_TEXT6,WorkOrderTypeName,WOTYPE3
    MSSQL_ADO_QUERY_FEATURE_TYPES_FOR_MERGE_FILTERS = Yes
    MSSQL_ADO_NAMED_CONNECTION = TrackIT
    RESULT -> amd.workorders (writer POSTGRES_1)
amd.workorders (writer POSTGRES_1)
    attributes: id int4,PRIKEY, parent_id int4, respondby timestamp, summary varchar(100), type varchar(30), requestor varchar(50), requested_date timestamp, resolution_date timestamp, elapsed_time varchar(20), priority varchar(50), due_date timestamp, assigned_technician varchar(30), date_completed timestamp, hours float4, department varchar(30), notes text, resolution text, current_status varchar(255), incident_or_service_req varchar(50), hotlist varchar(50), date_responded timestamp, work_order_type_name varchar(255), sub_type varchar(30), text1 varchar(40), text4 varchar(40), forward_project varchar(50), org_impact varchar(50), requestor_priority varchar(50), task_lookup_6 varchar(50), task_lookup_7 varchar(50),
      it_involvement varchar(50), assndate timestamp, wo_type_3 varchar(30), status varchar(25), wo_text_2 varchar(40), wo_text_3 varchar(40), wo_text_5 varchar(40), wo_text_6 varchar(40), wo_num_1 float4, wo_int_1 int4
