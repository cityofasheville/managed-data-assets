FME workspace munisTOwh-general_ledger_parameters.fmw

Parameters:
- SourceDataset_MSSQL_ADO_3 = munis-prod   # SQL Server Connection
- DestDataset_POSTGRES = mda-store-1   # Connection

Readers:
- MSSQL_ADO_1: MSSQL_ADO from $(SourceDataset_MSSQL_ADO_3)

Writers:
- POSTGRES_1: POSTGRES to $(DestDataset_POSTGRES)

dbo.GeneralLedgerParameters (reader MSSQL_ADO_1)
    attributes: Id identity, Parm char(1), BudgetRequest_Level1_Description varchar(10), BudgetRequest_Level2_Description varchar(10), BudgetRequest_Level3_Description varchar(10), BudgetRequest_Level4_Description varchar(10), BudgetRequest_Level5_Description varchar(10), UseProjectCode bit, UseBudgetaryControl bit, DefaultYear smallint, DefaultPeriod smallint, BudgetCarryForwardMethod char(1), CurrentYear smallint, CurrentPeriod smallint, BeginningFiscalYearDate datetime, EndFiscalYearDate datetime, IsCurrentYearHeldOpen bit, FinalBudgetLevel smallint, BalanceSegment1_Length smallint, BalanceSegment2_Length smallint, BalanceSegment3_Length smallint, BalanceSegment4_Length smallint, BalanceSegment5_Length smallint, BalanceSegment6_Length smallint, BalanceSegment7_Length smallint, BalanceSegment8_Length smallint, ExpenseSegment1_Length smallint, ExpenseSegment2_Length smallint, ExpenseSegment3_Length smallint, ExpenseSegment4_Length smallint,
      ExpenseSegment5_Length smallint, ExpenseSegment6_Length smallint, ExpenseSegment7_Length smallint, ExpenseSegment8_Length smallint, RevenueSegment1_Length smallint, RevenueSegment2_Length smallint, RevenueSegment3_Length smallint, RevenueSegment4_Length smallint, RevenueSegment5_Length smallint, RevenueSegment6_Length smallint, RevenueSegment7_Length smallint, RevenueSegment8_Length smallint, Segment1_LongDescription varchar(12), Segment2_LongDescription varchar(12), Segment3_LongDescription varchar(12), Segment4_LongDescription varchar(12), Segment5_LongDescription varchar(12), Segment6_LongDescription varchar(12), Segment7_LongDescription varchar(12), Segment8_LongDescription varchar(12), Segment1_ShortDescription varchar(4), Segment2_ShortDescription varchar(4), Segment3_ShortDescription varchar(4), Segment4_ShortDescription varchar(4), Segment5_ShortDescription varchar(4), Segment6_ShortDescription varchar(4), Segment7_ShortDescription varchar(4), Segment8_ShortDescription varchar(4), TotalSegments smallint, Delimiter char(1),
      GrantSegment smallint, GrantExpCatSegment smallint, IncludeReqAmountsInBudgetChecks bit, YearEnd bit, BalanceToSegment char(1), AccountCodeCheck bit, AllowRevenueAccountsWithEncumbrance bit, EnforceDefaultYear bit, IsRollupCodePromptActive bit, AccountRestrictionForMultipleRoles char(1), ScheduledUpdateDefaultPeriod integer, SynchronizationFormatCode varchar(10), JournalExportFormat varchar(10), DisplayLongObject bit, DefaultJournalStatus char(1), AutoPostJournal bit, AutoCreateGeneralBilling bit, PostDateFlag char(1), Summ_Pr_Je char(1), Pocan_CarryForwardBudget char(1), PODefaultYear smallint, PODefaultPeriod smallint, ARDefaultYear smallint, ARDefaultPeriod smallint, ContJournal char(1), NextYearBua char(1), Version timestamp, PCashFund varchar(4), FiscalYearStartMonthId integer, VerifyCashLevel bit,
      EnforceCFWDBudget bit, AutoGenerateDTDF bit, UseNYRollups bit, UseGeneroJournalEntry bit
    -> public.general_ledger_parameters (writer POSTGRES_1)
public.general_ledger_parameters (writer POSTGRES_1)
    attributes: id int4, parm char(1), budgetrequest_level1_description varchar(10), budgetrequest_level2_description varchar(10), budgetrequest_level3_description varchar(10), budgetrequest_level4_description varchar(10), budgetrequest_level5_description varchar(10), useprojectcode bool, usebudgetarycontrol bool, defaultyear int2, defaultperiod int2, budgetcarryforwardmethod char(1), currentyear int2, currentperiod int2, beginningfiscalyeardate timestamp, endfiscalyeardate timestamp, iscurrentyearheldopen bool, finalbudgetlevel int2, balancesegment1_length int2, balancesegment2_length int2, balancesegment3_length int2, balancesegment4_length int2, balancesegment5_length int2, balancesegment6_length int2, balancesegment7_length int2, balancesegment8_length int2, expensesegment1_length int2, expensesegment2_length int2, expensesegment3_length int2, expensesegment4_length int2,
      expensesegment5_length int2, expensesegment6_length int2, expensesegment7_length int2, expensesegment8_length int2, revenuesegment1_length int2, revenuesegment2_length int2, revenuesegment3_length int2, revenuesegment4_length int2, revenuesegment5_length int2, revenuesegment6_length int2, revenuesegment7_length int2, revenuesegment8_length int2, segment1_longdescription varchar(12), segment2_longdescription varchar(12), segment3_longdescription varchar(12), segment4_longdescription varchar(12), segment5_longdescription varchar(12), segment6_longdescription varchar(12), segment7_longdescription varchar(12), segment8_longdescription varchar(12), segment1_shortdescription varchar(4), segment2_shortdescription varchar(4), segment3_shortdescription varchar(4), segment4_shortdescription varchar(4), segment5_shortdescription varchar(4), segment6_shortdescription varchar(4), segment7_shortdescription varchar(4), segment8_shortdescription varchar(4), totalsegments int2, delimiter char(1),
      grantsegment int2, grantexpcatsegment int2, includereqamountsinbudgetchecks bool, yearend bool, balancetosegment char(1), accountcodecheck bool, allowrevenueaccountswithencumbrance bool, enforcedefaultyear bool, isrollupcodepromptactive bool, accountrestrictionformultipleroles char(1), scheduledupdatedefaultperiod int4, synchronizationformatcode varchar(10), journalexportformat varchar(10), displaylongobject bool, defaultjournalstatus char(1), autopostjournal bool, autocreategeneralbilling bool, postdateflag char(1), summ_pr_je char(1), pocan_carryforwardbudget char(1), podefaultyear int2, podefaultperiod int2, ardefaultyear int2, ardefaultperiod int2, contjournal char(1), nextyearbua char(1), version bytea, pcashfund varchar(4), fiscalyearstartmonthid int4, verifycashlevel bool,
      enforcecfwdbudget bool, autogeneratedtdf bool, usenyrollups bool, usegenerojournalentry bool
