FME workspace budget_mapping_sheet2wh.fmw

Parameters:
- DestDataset_POSTGRES = coa-pg-db1   # Connection
- DestDataset_POSTGRES_9 = coa-pg-db1   # Connection
- DestDataset_POSTGRES_13 = coa-pg-db1   # Connection
- DestDataset_POSTGRES_11 = coa-pg-db1   # Connection
- DestDataset_POSTGRES_8 = coa-pg-db1   # Connection
- DestDataset_POSTGRES_10 = coa-pg-db1   # Connection
- DestDataset_POSTGRES_12 = coa-pg-db1   # Connection

Readers:
- GOOGLESHEETS_1: GOOGLESHEETS
- GOOGLESHEETS_2: GOOGLESHEETS
- GOOGLESHEETS_3: GOOGLESHEETS
- GOOGLESHEETS_4: GOOGLESHEETS
- GOOGLESHEETS_5: GOOGLESHEETS
- GOOGLESHEETS_6: GOOGLESHEETS
- GOOGLESHEETS_7: GOOGLESHEETS

Writers:
- POSTGRES_1: POSTGRES to $(DestDataset_POSTGRES)
- POSTGRES_2: POSTGRES to $(DestDataset_POSTGRES_9)
- POSTGRES_3: POSTGRES to $(DestDataset_POSTGRES_13)
- POSTGRES_4: POSTGRES to $(DestDataset_POSTGRES_11)
- POSTGRES_5: POSTGRES to $(DestDataset_POSTGRES_8)
- POSTGRES_6: POSTGRES to $(DestDataset_POSTGRES_10)
- POSTGRES_7: POSTGRES to $(DestDataset_POSTGRES_12)

categories (reader GOOGLESHEETS_1)
    attributes: id text, category text
    -> budget_categories (writer POSTGRES_1)
budget_categories (writer POSTGRES_1)
    attributes: id int4,PRIKEY, category text
deptdiv_mappings (reader GOOGLESHEETS_7)
    attributes: dept_id1 text, div_id1 text, dept_id2 text, div_id2 text, department_name text, division_name text
    -> budget_deptdiv_mappings (writer POSTGRES_7)
budget_deptdiv_mappings (writer POSTGRES_7)
    attributes: dept_id1 text, div_id1 text, dept_id2 text, div_id2 text, department_name text, division_name text
budget_sections (reader GOOGLESHEETS_2)
    attributes: ID text, budget_section text
    -> budget_sections (writer POSTGRES_2)
budget_sections (writer POSTGRES_2)
    attributes: id int4,PRIKEY, budget_section text
category_mapping (reader GOOGLESHEETS_3)
    attributes: object_code text, category text, description text
    -> budget_category_mapping (writer POSTGRES_3)
budget_category_mapping (writer POSTGRES_3)
    attributes: object_code text, category int4, description text
budget_section_mapping (reader GOOGLESHEETS_4)
    attributes: org_code text, object_code text, budget_section text, description text
    -> budget_section_mapping (writer POSTGRES_4)
budget_section_mapping (writer POSTGRES_4)
    attributes: org_code text, object_code text, budget_section int4, description text
exclusions (reader GOOGLESHEETS_5)
    attributes: org_code text, object_code text
    -> budget_exclusions (writer POSTGRES_5)
budget_exclusions (writer POSTGRES_5)
    attributes: org_code text, object_code text
interfund_transfers (reader GOOGLESHEETS_6)
    attributes: org_code text, object_code text
    -> budget_interfund_transfers (writer POSTGRES_6)
budget_interfund_transfers (writer POSTGRES_6)
    attributes: org_code text, object_code text
