FME workspace munis_gl_master_cip.fmw

Parameters:
- SourceDataset_MSSQL_ADO = @coamunisdb1/mu_live   # SQL Server Connection
- DestDataset_POSTGRES_3 = datastore1   # Connection
- SourceDataset_MSSQL_ADO_3 = munis-prod   # SQL Server Connection

Readers:
- MSSQL_ADO_1: MSSQL_ADO from $(SourceDataset_MSSQL_ADO)
- MSSQL_ADO_2: MSSQL_ADO from $(SourceDataset_MSSQL_ADO_3)

Writers:
- POSTGRES_1: POSTGRES to $(DestDataset_POSTGRES_3)

dbo.gl_master (reader MSSQL_ADO_2)
    attributes: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
dbo.gl_master (reader MSSQL_ADO_1) [off]
    attributes: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
SQLCreator_2
    SQL_STATEMENT:
      SELECT        TOP (100) PERCENT a_account_type AS AccountType, a_fund_seg1 AS Fund,
      a_object AS ObjectId, a_object_desc AS ObjDesc,
      a_project AS ProjectId,
                               a_org AS OrgId, a_org_description AS OrgDesc,
                                a_account_status AS AccountStatus,
                               a_segment_3 AS DeptId,
                               a_segment_4 AS DivId, a_segment_5 AS Costcenter,
                               a_charcode_desc AS CharcodeDesc,
                                my_orig_bud_ltd AS LifeOriginalBudget,
                               my_bud_xfr_in_ltd AS LifeTransfersIn,
                               my_bud_xfr_in_ltd AS LifeTransfersOut,
                               my_rev_bud_ltd AS LifeRevisedBudget,
                               b_cy_memo_bal AS CYActualMemoBalance,
                               b_cy_encumb AS CYEncumbrances, b_ly1_actual_bal AS Actuals2017,
                               b_ly2_actual_bal AS Actuals2016, b_ly3_actual_bal AS Actuals2015,
                               b_ly4_actual_bal AS Actuals2014, b_ly5_actual_bal AS Actuals2013,
                               b_ly6_actual_bal AS Actuals2012, b_ly7_actual_bal AS Actuals2011
      FROM            dbo.gl_master
      WHERE        (ISNULL(a_project, '') <> '') AND a_project NOT LIKE 'A%' AND a_project NOT LIKE 'D%'
      ORDER BY ProjectId




      --AND a_project NOT LIKE 'B%'
    MSSQL_SPATIAL_COMMAND_TIMEOUT = 30
    FORMAT = MSSQL_SPATIAL
    MSSQL_SPATIAL_QUERY_FEATURE_TYPES_FOR_MERGE_FILTERS = Yes
    EXPOSED_ATTRIBUTE_LIST = AccountStatus,AccountType,Actuals2011,Actuals2012,Actuals2013,Actuals2014,Actuals2015,Actuals2016,Actuals2017,CharcodeDesc,Costcenter,CYActualMemoBalance,CYEncumbrances,DeptId,DivId,Fund,LifeOriginalBudget,LifeRevisedBudget,LifeTransfersIn,LifeTransfersOut,ObjDesc,ObjectId,OrgDesc,OrgId,ProjectId
    MSSQL_SPATIAL_NAMED_CONNECTION = munis-prod
    DATASET = munis-prod
    RESULT -> amd.munis_gl_master_cip (writer POSTGRES_1)
amd.munis_gl_master_cip (writer POSTGRES_1)
    attributes: accountstatus varchar(200), accounttype varchar(200), actuals2011 varchar(200), actuals2012 varchar(200), actuals2013 varchar(200), actuals2014 varchar(200), actuals2015 varchar(200), actuals2016 varchar(200), actuals2017 varchar(200), charcodedesc varchar(200), costcenter varchar(200), cyactualmemobalance varchar(200), cyencumbrances varchar(200), deptid varchar(200), divid varchar(200), fund varchar(200), lifeoriginalbudget varchar(200), liferevisedbudget varchar(200), lifetransfersin varchar(200), lifetransfersout varchar(200), objdesc varchar(200), objectid varchar(200), orgdesc varchar(200), orgid varchar(200), projectid varchar(200)
