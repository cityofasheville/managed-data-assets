FME workspace cip_master_sheet_to_dashboard.fmw

Parameters:
- DestDataset_POSTGRES = datastore1   # Connection

Readers:
- GOOGLESHEETS_1: GOOGLESHEETS

Writers:
- POSTGRES_1: POSTGRES to $(DestDataset_POSTGRES)

General Project Information (reader GOOGLESHEETS_1)
    attributes: GIS_ID text, MUNIS Project Number text, Project text, Display Name text, Location Details text, Zip Code text, Category text, COA Contact text, Phone Number text, Email Address text, Owner Department text, Administering Department text, Project Description text, Status text, GO Bond Funding text, CIP Funding (total) text, Grant Funding (total) text, Other Funding text, Total Project Funding (Budget Document) text, Preliminary Project Budget (planning phase estimate) text, Estimated Total Project Cost text, Total Spent text, Target Construction Start text, Target Construction End text, Actual Construction End text, Amount behind Schedule text, Estimated Construction Duration text, Project Folder text, Project Webpage (more information) text, Communication Plan text,
      Photo URL text, Map Tab text, Project Updates text, Where? text, CONTACT text
    -> amd.coa_cip_project_information (writer POSTGRES_1)
amd.coa_cip_project_information (writer POSTGRES_1)
    attributes: gis_id text, munis_project_number text, project text, display_name text, location_details text, zip_code text, category text, coa_contact text, phone_number text, email_address text, owner_department text, administering_department text, project_description text, status text, go_bond_funding text, cip_funding__total_ text, grant_funding__total_ text, other_funding text, total_project_funding__budget_document_ text, preliminary_project_budget__planning_phase_estimate_ text, estimated_total_project_cost text, total_spent text, target_construction_start text, target_construction_end text, actual_construction_end text, amount_behind_schedule text, estimated_construction_duration text, project_folder text, project_webpage__more_information_ text, communication_plan text,
      photo_url text, map_tab text, project_updates text, where_ text, contact text
