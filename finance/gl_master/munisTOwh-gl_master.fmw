FME workspace munisTOwh-gl_master.fmw

Parameters:
- SourceDataset_MSSQL_ADO = munis-prod   # SQL Server Connection
- DestDataset_POSTGRES = mda-store-1   # Connection

Readers:
- MSSQL_ADO_1: MSSQL_ADO from $(SourceDataset_MSSQL_ADO)

Writers:
- POSTGRES_2: POSTGRES to $(DestDataset_POSTGRES)

amd.gl_master (reader MSSQL_ADO_1)
    attributes: account_type char(1), account_status char(1), fund_name varchar(30), function_name varchar(30), department_name varchar(30), division_name varchar(30), costcenter_name varchar(30), grant_name varchar(30), organization_name char(30), object_name char(30), project_name varchar(35), year integer, original_budget numeric(13,2), revised_budget numeric(13,2), actual numeric(13,2), memo numeric(13,2), cy_encumbrances numeric(13,2), lifetime_original_budget numeric(13,2), lifetime_revised_budget numeric(13,2), life_transfers_in numeric(13,2), life_transfers_out numeric(13,2), fund_id varchar(10), function_id varchar(10), department_id varchar(10), division_id varchar(10), costcenter_id varchar(10), grant_id varchar(10), organization_id varchar(8), object_id varchar(6), project_id varchar(10),
      full_account_id char(55), charcode_name varchar(20), is_budgetary char(1)
    -> public.gl_master (writer POSTGRES_2)
public.gl_master (writer POSTGRES_2)
    attributes: account_type char(1), account_status char(1), fund_name varchar(30), function_name varchar(30), department_name varchar(30), division_name varchar(30), costcenter_name varchar(30), grant_name varchar(30), organization_name char(30), object_name char(30), project_name varchar(35), year int4, original_budget numeric(13,2), revised_budget numeric(13,2), actual numeric(13,2), memo numeric(13,2), cy_encumbrances numeric(13,2), lifetime_original_budget numeric(13,2), lifetime_revised_budget numeric(13,2), life_transfers_in numeric(13,2), life_transfers_out numeric(13,2), fund_id varchar(10), function_id varchar(10), department_id varchar(10), division_id varchar(10), costcenter_id varchar(10), grant_id varchar(10), organization_id varchar(8), object_id varchar(6), project_id varchar(10),
      full_account_id char(55), charcode_name varchar(20), is_budgetary char(1)
