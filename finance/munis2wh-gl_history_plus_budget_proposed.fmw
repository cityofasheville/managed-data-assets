FME workspace munis2wh-gl_history_plus_budget_proposed.fmw

Parameters:
- SourceDataset_MSSQL_ADO = @coamunisdb1/mu_live   # SQL Server Connection
- DestDataset_POSTGRES = coa-pg-db1   # Connection

Readers:
- MSSQL_ADO_1: MSSQL_ADO from $(SourceDataset_MSSQL_ADO)

Writers:
- POSTGRES_1: POSTGRES to $(DestDataset_POSTGRES)

amd.gl_history_plus_budget_proposed (reader MSSQL_ADO_1)
    attributes: account_type char(1), account_name char(30), fund_name varchar(30), department_name varchar(30), division_name varchar(30), costcenter_name varchar(30), function_name varchar(30), charcode_name varchar(20), organization_name char(30), object_name char(30), year integer, budget numeric(16,3), actual numeric(16,3), full_account_id char(55), org_id varchar(8), obj_id varchar(6), fund_id varchar(10), dept_id varchar(10), div_id varchar(10), cost_id varchar(10), func_id varchar(10), charcode char(2), proj_id varchar(10), is_proposed varchar(5)
    -> coagis.gl_history_plus_budget_proposed (writer POSTGRES_1)
coagis.gl_history_plus_budget_proposed (writer POSTGRES_1)
    attributes: account_type char(1), account_name char(30), fund_name varchar(30), department_name varchar(30), division_name varchar(30), costcenter_name varchar(30), function_name varchar(30), charcode_name varchar(20), organization_name char(30), object_name char(30), year int4, budget numeric(16,3), actual numeric(16,3), full_account_id char(55), org_id varchar(8), obj_id varchar(6), fund_id varchar(10), dept_id varchar(10), div_id varchar(10), cost_id varchar(10), func_id varchar(10), charcode char(2), proj_id varchar(10), is_proposed varchar(5)
