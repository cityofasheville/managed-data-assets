FME workspace munis2wh-gl_budget.fmw

Parameters:
- DestDataset_POSTGRES = datastore1   # Connection
- SourceDataset_MSSQL_ADO_3 = munis-prod   # SQL Server Connection

Readers:
- MSSQL_ADO_2: MSSQL_ADO from $(SourceDataset_MSSQL_ADO_3)

Writers:
- POSTGRES_1: POSTGRES to $(DestDataset_POSTGRES)

amd.gl_budget (reader MSSQL_ADO_2)
    attributes: account_type char(1), account_status char(1), fund_name varchar(30), function_name varchar(30), department_name varchar(30), division_name varchar(30), costcenter_name varchar(30), grant_name varchar(30), organization_name char(30), object_name char(30), project_name varchar(35), year smallint, proposed_budget numeric(13,2), adopted_budget numeric(13,2), fund_id varchar(10), function_id varchar(10), department_id varchar(10), division_id varchar(10), costcenter_id varchar(10), grant_id varchar(10), organization_id varchar(8), object_id varchar(6), project_id varchar(10), full_account_id char(55), charcode_name varchar(20)
    -> amd.gl_budget (writer POSTGRES_1)
amd.gl_budget (writer POSTGRES_1)
    attributes: account_type char(1), account_status char(1), fund_name varchar(30), function_name varchar(30), department_name varchar(30), division_name varchar(30), costcenter_name varchar(30), grant_name varchar(30), organization_name char(30), object_name char(30), project_name varchar(35), year int2, proposed_budget numeric(13,2), adopted_budget numeric(13,2), fund_id varchar(10), function_id varchar(10), department_id varchar(10), division_id varchar(10), costcenter_id varchar(10), grant_id varchar(10), organization_id varchar(8), object_id varchar(6), project_id varchar(10), full_account_id char(55), charcode_name varchar(20)
