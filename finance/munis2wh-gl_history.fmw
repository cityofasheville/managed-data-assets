FME workspace munis2wh-gl_history.fmw

Parameters:
- SourceDataset_MSSQL_ADO_3 = @coamunisdb1/mu_live   # SQL Server Connection
- DestDataset_POSTGRES = coa-pg-db1   # Connection

Readers:
- MSSQL_ADO_1: MSSQL_ADO from $(SourceDataset_MSSQL_ADO_3)

Writers:
- POSTGRES_1: POSTGRES to $(DestDataset_POSTGRES)

amd.gl_history (reader MSSQL_ADO_1)
    attributes: account_type char(1), account_name char(30), fund_name varchar(30), department_name varchar(30), division_name varchar(30), costcenter_name varchar(30), function_name varchar(30), charcode_name varchar(20), organization_name char(30), object_name char(30), year integer, original_budget numeric(13,2), actual numeric(13,2), memo numeric(13,2), full_account_id char(55), acct_uid integer, org_id varchar(8), obj_id varchar(6), fund_id varchar(10), dept_id varchar(10), div_id varchar(10), cost_id varchar(10), func_id varchar(10), charcode char(2), proj_id varchar(10), is_budgetary char(1), acct_status char(1)
    -> coagis.gl_history (writer POSTGRES_1)
coagis.gl_history (writer POSTGRES_1)
    attributes: account_type char(1), account_name char(30), fund_name varchar(30), department_name varchar(30), division_name varchar(30), costcenter_name varchar(30), function_name varchar(30), charcode_name varchar(20), organization_name char(30), object_name char(30), year int4, original_budget numeric(13,2), actual numeric(13,2), memo numeric(13,2), full_account_id char(55), acct_uid int4, org_id varchar(8), obj_id varchar(6), fund_id varchar(10), dept_id varchar(10), div_id varchar(10), cost_id varchar(10), func_id varchar(10), charcode char(2), proj_id varchar(10), is_budgetary char(1), acct_status char(1)
