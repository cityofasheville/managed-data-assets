FME workspace editTOwh-coa_districts_zoning.fmw

Parameters:
- DestDataset_POSTGIS_3 = mda-store-1   # Connection

Readers:
- GEODATABASE_SDE_1: GEODATABASE_SDE

Writers:
- POSTGIS_1: POSTGIS to $(DestDataset_POSTGIS_3)

coa_districts_zoning (reader GEODATABASE_SDE_1)
    attributes: objectid integer, districts char(12), municodepage char(254), acreage double, squaremiles double, pp_weight smallint, edit_date date, edit_by char(100), pid integer, max_impervious double, date date, ordinance char(50), st_area(shape) double, st_length(shape) double
    -> coa_districts_zoning (writer POSTGIS_1)
coa_districts_zoning (writer POSTGIS_1)
    attributes: objectid int4, districts varchar(12), municodepage varchar(254), acreage float8, squaremiles float8, pp_weight int2, edit_date timestamp, edit_by varchar(100), pid int4, max_impervious float8, date timestamp, ordinance varchar(50), st_area_shape_ float8, st_length_shape_ float8
