FME workspace bcTOwh-bc_location2.fmw

Parameters:
- DestDataset_POSTGRES_5 = coa-pg-db1   # Connection
- DestDataset_POSTGRES = mda-store-1   # Connection
- DestDataset_POSTGIS = mda-store-1   # Connection

Readers:
- GEODATABASE_SDE_1: GEODATABASE_SDE in EPSG:2264

Writers:
- POSTGRES_1: POSTGRES
- POSTGRES_2: POSTGRES to $(DestDataset_POSTGRES)
- POSTGIS_1: POSTGIS to $(DestDataset_POSTGIS)

location (reader GEODATABASE_SDE_1)
    attributes: OBJECTID integer, LOCATION_ID double, LOCATIONTYPE integer, CIVICADDRESS_ID double, PARENT_LOCATION_ID double, BUILDING_ID double, CENTERLINE_ID double, USER_ID char(8), ESN smallint, X_COORD double, Y_COORD double, COMMCODE char(4), PRIMARY_STRUCTURE smallint, CREATE_DATE date, CHANGE_DATE date, PARCEL_ID char(10)
    -> CREATE_DATE2
CREATE_DATE2: DateFormatter
    SRCFMT = Unknown - Automatic Detection
    FMT = FME Date/Time (%Y%m%d%H%M%S)
    DATE_ATTR = CREATE_DATE
    INVALID_DATE_VALUE = _FME_NO_OP_
    -> bc_location (writer POSTGIS_1)
bc_location (writer POSTGIS_1)
    attributes: objectid int4, location_id float8, locationtype int4, civicaddress_id float8, parent_location_id float8, building_id float8, centerline_id float8, user_id varchar(8), esn int2, x_coord float8, y_coord float8, commcode varchar(4), primary_structure int2, create_date timestamp, change_date timestamp, parcel_id varchar(10)
