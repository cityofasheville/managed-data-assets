FME workspace cincinnatiTOmdastore1-parking_cincinnati_rv_exits.fmw

Parameters:
- SourceDataset_MSSQL_ADO = cinncinati_parking   # SQL Server Connection
- DestDataset_POSTGRES = mda-store-1   # Connection

Readers:
- MSSQL_ADO_1: MSSQL_ADO from $(SourceDataset_MSSQL_ADO)

Writers:
- POSTGRES_1: POSTGRES to $(DestDataset_POSTGRES)

dbo.RV_EXITS (reader MSSQL_ADO_1)
    attributes: TRANSACTION_STAMP varchar(40), DEVICE_KEY varchar(20), MACHINE_NUMBER smallint, DEVICE_TYPE smallint, CENTRAL_PAY smallint, FIRMWARE smallint, ATTENDANT smallint, ATTENDANT_OVERRIDE smallint, ENTRY_TIME datetime, EXIT_TIME datetime, TRANSACTION_NUMBER integer, TRANSACTION_TYPE smallint, CENTRAL_PAY_SENT smallint, COMPLIMENTARY smallint, VALIDATED smallint, TICKET bigint, TICKET_TYPE varchar(2), DISPENSER smallint, RATE varchar(2), RATE_TYPE smallint, GROSS money, NET money, CASH_AMOUNT money, TENDERED money, SHORT_MONEY money, CHANGE money, CURRENCY_TYPE smallint, EXCHANGE float, NUM_VAL smallint, MISC_KEY smallint,
      MISC_AMOUNT money, TAX money, TAX_OVERRULED smallint, CARD_TYPE smallint, CARD_NUMBER integer, CARD_AMOUNT money, CHECK_NUMBER integer, CHECK_AMOUNT money, NUM_DISCOUNT smallint, AMT_DISCOUNT money, EXIT_COUNT smallint, PAYMENT_TYPE smallint
    -> internal.parking_cincinnati_rv_exits (writer POSTGRES_1)
internal.parking_cincinnati_rv_exits (writer POSTGRES_1)
    attributes: transaction_stamp varchar(40), device_key varchar(20), machine_number int2, device_type int2, central_pay int2, firmware int2, attendant int2, attendant_override int2, entry_time timestamp, exit_time timestamp, transaction_number int4, transaction_type int2, central_pay_sent int2, complimentary int2, validated int2, ticket int8, ticket_type varchar(2), dispenser int2, rate varchar(2), rate_type int2, gross float8, net float8, cash_amount float8, tendered float8, short_money float8, change float8, currency_type int2, exchange float8, num_val int2, misc_key int2,
      misc_amount float8, tax float8, tax_overruled int2, card_type int2, card_number int4, card_amount float8, check_number int4, check_amount float8, num_discount int2, amt_discount float8, exit_count int2, payment_type int2
