FME workspace cincinnatiTOmdastore1-parking_cincinnati_contract_activity.fmw

Parameters:
- SourceDataset_MSSQL_ADO = cinncinati_parking   # SQL Server Connection
- DestDataset_POSTGRES = mda-store-1   # Connection

Readers:
- MSSQL_ADO_1: MSSQL_ADO from $(SourceDataset_MSSQL_ADO)

Writers:
- POSTGRES_1: POSTGRES to $(DestDataset_POSTGRES)

dbo.CONTRACT_ACTIVITY (reader MSSQL_ADO_1)
    attributes: CARD_NUM integer, READER integer, DIRECTION smallint, ACTIVITY_TIME datetime, CODE smallint, ALLOW smallint, TICKET integer, DEBIT_TYPE smallint, DEBIT_FEE real, DEBIT_VALUE real, CREDIT_CARD_TYPE smallint, CREDIT_CARD_NUMBER nvarchar(20), CREDIT_CARD_EXPIRATION datetime, VALET_TICKET integer, THRESHOLD integer, TRANSACTION_NUMBER integer, APPROVAL_CODE nvarchar(20), ACCESS_GROUP integer, RATE nvarchar(20), GROSS_DEBIT_FEE real, VALIDATION_AMT real, VALIDATION_NUM integer, VALIDATION_AMT2 real, VALIDATION_NUM2 integer, VALIDATION_AMT3 real, VALIDATION_NUM3 integer, VALIDATION_AMT4 real, VALIDATION_NUM4 integer, VALIDATION_COUNT integer, VALIDATION_COUNT2 integer,
      VALIDATION_COUNT3 integer, VALIDATION_COUNT4 integer, CREDIT_CARD_ENTRANCE datetime, LOT_NUMBER smallint, SMART_CARD_BASE varchar(32), SMART_CARD_ID varchar(32), ImageID integer, CREDIT_CARD_TRANSACTION integer, ID identity, SYSTEM_CODE integer
    -> internal.parking_cincinnati_contract_activity (writer POSTGRES_1)
internal.parking_cincinnati_contract_activity (writer POSTGRES_1)
    attributes: card_num int4, reader int4, direction int2, activity_time timestamp, code int2, allow int2, ticket int4, debit_type int2, debit_fee float4, debit_value float4, credit_card_type int2, credit_card_number varchar(20), credit_card_expiration timestamp, valet_ticket int4, threshold int4, transaction_number int4, approval_code varchar(20), access_group int4, rate varchar(20), gross_debit_fee float4, validation_amt float4, validation_num int4, validation_amt2 float4, validation_num2 int4, validation_amt3 float4, validation_num3 int4, validation_amt4 float4, validation_num4 int4, validation_count int4, validation_count2 int4,
      validation_count3 int4, validation_count4 int4, credit_card_entrance timestamp, lot_number int2, smart_card_base varchar(32), smart_card_id varchar(32), imageid int4, credit_card_transaction int4, id int4, system_code int4
