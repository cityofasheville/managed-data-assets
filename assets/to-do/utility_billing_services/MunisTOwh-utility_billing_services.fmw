FME workspace MunisTOwh-utility_billing_services.fmw

Parameters:
- DestDataset_POSTGRES = coa-gis-warehouse1   # Connection

Writers:
- POSTGRES_1: POSTGRES to $(DestDataset_POSTGRES)

SQLCreator
    SQL_STATEMENT:
      	SELECT DISTINCT a_service_mast_key, row3.a_acct_cust_key, row4.a_account, a_ar_customer_cid,
      	am_start_date, am_stop_date, am_account_type, am_parcel civicaddress_id, am_district, am_location_unit,
      	am_location_city, am_location_lot, am_street_number, am_location_suffix, am_loc_pre_dir,
      	am_loc_state, am_loc_street_type, am_location_street, am_loc_post_dir, am_loc_subdivision,
      	am_loc_unit_type, am_loc_zip_code, service
      	FROM (
      		SELECT a_service_mast_key, a_acct_cust_key, a_service_code
      		FROM dbo.ut_service_master
      		WHERE sm_service_status = 'A'
      	) AS row3
      	INNER JOIN (
      		SELECT arcode.hg_code, hg_description1 AS service
      		FROM	dbo.ar_charge_arcode arcode
      		INNER JOIN (
      			SELECT hg_code, MAX(hg_year) maxyear
      			FROM	dbo.ar_charge_arcode
      			GROUP BY hg_code
      		) AS latest
      		ON arcode.hg_code = latest.hg_code
      		AND arcode.hg_year = latest.maxyear
      	) AS row2
      	ON row3.a_service_code = row2.hg_code
      	INNER JOIN (
      		SELECT a_acct_cust_key,a_account,a_ar_customer_cid
      		FROM	ut_customers
      	) AS row4
      	ON row4.a_acct_cust_key = row3.a_acct_cust_key
      	INNER JOIN (
      		SELECT a_account_key,a_account,am_start_date,
      		am_stop_date,am_account_type,
      		CAST(IIF(ISNULL(am_parcel,'')='','0.0',LEFT(am_parcel,9)) AS Float) AS am_parcel,
      		am_property_desc,am_district,am_location_unit,
      		am_location_city,am_location_lot,am_street_number,
      		am_location_suffix,am_loc_post_dir,am_loc_pre_dir,
      		am_loc_state,am_loc_street_type,am_location_street,
      		am_loc_subdivision,am_loc_unit_type,am_loc_zip_code,
      		am_acct_add_date,am_read_sequence,am_route_book,
      		am_911_address,am_valid_address,am_floor_drain,
      		am_converted_flag,am_filler,am_line_type,
      		am_material_used,am_sump_pump_flag,
      		am_bkflow_dev_req,am_alt_parcel
      		FROM	ut_account_master
      		WHERE ISNUMERIC(am_parcel) <> 0
      	) AS row6
      	ON row6.a_account = row4.a_account
    EXPOSED_ATTRIBUTE_LIST = a_account,a_acct_cust_key,a_ar_customer_cid,a_service_mast_key,am_account_type,am_district,am_loc_post_dir,am_loc_pre_dir,am_loc_state,am_loc_street_type,am_loc_subdivision,am_loc_unit_type,am_loc_zip_code,am_location_city,am_location_lot,am_location_street,am_location_suffix,am_location_unit,am_start_date,am_stop_date,am_street_number,civicaddress_id,service
    MSSQL_ADO_QUERY_FEATURE_TYPES_FOR_MERGE_FILTERS = Yes
    DATASET = munis-prod
    FORMAT = MSSQL_ADO
    MSSQL_ADO_NAMED_CONNECTION = munis-prod
    MSSQL_ADO_COMMAND_TIMEOUT = 600
    RESULT -> Counter
Counter
    START = 0
    DOMAIN = counter
    SCOPE = Global
    CNT_ATTR = pid
    -> munis_utility_billing_services_etl_table (writer POSTGRES_1)
munis_utility_billing_services_etl_table (writer POSTGRES_1)
    attributes: a_account varchar(200), a_acct_cust_key varchar(200), a_ar_customer_cid varchar(200), a_service_mast_key varchar(200), am_account_type varchar(200), am_district varchar(200), am_loc_post_dir varchar(200), am_loc_pre_dir varchar(200), am_loc_state varchar(200), am_loc_street_type varchar(200), am_loc_subdivision varchar(200), am_loc_unit_type varchar(200), am_loc_zip_code varchar(200), am_location_city varchar(200), am_location_lot varchar(200), am_location_street varchar(200), am_location_suffix varchar(200), am_location_unit varchar(200), am_start_date varchar(200), am_stop_date varchar(200), am_street_number varchar(200), civicaddress_id varchar(200), service varchar(200), pid varchar(200)
