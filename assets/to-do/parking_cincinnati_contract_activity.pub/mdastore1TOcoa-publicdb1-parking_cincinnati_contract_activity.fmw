FME workspace mdastore1TOcoa-publicdb1-parking_cincinnati_contract_activity.fmw

Parameters:
- SourceDataset_POSTGRES = mda-store-1   # Connection
- DestDataset_POSTGRES = coa-publicdb1   # Connection

Readers:
- POSTGRES_1: POSTGRES from $(SourceDataset_POSTGRES)

Writers:
- POSTGRES_2: POSTGRES to $(DestDataset_POSTGRES)

internal.parking_cincinnati_contract_activity (reader POSTGRES_1)
    attributes: card_num int4, reader int4, direction int2, activity_time timestamp, code int2, allow int2, ticket int4, debit_type int2, debit_fee float4, debit_value float4, credit_card_type int2, credit_card_number varchar(20), credit_card_expiration timestamp, valet_ticket int4, threshold int4, transaction_number int4, approval_code varchar(20), access_group int4, rate varchar(20), gross_debit_fee float4, validation_amt float4, validation_num int4, validation_amt2 float4, validation_num2 int4, validation_amt3 float4, validation_num3 int4, validation_amt4 float4, validation_num4 int4, validation_count int4, validation_count2 int4,
      validation_count3 int4, validation_count4 int4, credit_card_entrance timestamp, lot_number int2, smart_card_base varchar(32), smart_card_id varchar(32), imageid int4, credit_card_transaction int4, id int4, system_code int4
    -> smarking.parking_cincinnati_contract_activity (writer POSTGRES_2)
smarking.parking_cincinnati_contract_activity (writer POSTGRES_2)
    attributes: card_num int4, reader int4, direction int2, activity_time timestamp, code int2, allow int2, ticket int4, debit_type int2, debit_fee float4, debit_value float4, credit_card_type int2, credit_card_number varchar(20), credit_card_expiration timestamp, valet_ticket int4, threshold int4, transaction_number int4, approval_code varchar(20), access_group int4, rate varchar(20), gross_debit_fee float4, validation_amt float4, validation_num int4, validation_amt2 float4, validation_num2 int4, validation_amt3 float4, validation_num3 int4, validation_amt4 float4, validation_num4 int4, validation_count int4, validation_count2 int4,
      validation_count3 int4, validation_count4 int4, credit_card_entrance timestamp, lot_number int2, smart_card_base varchar(32), smart_card_id varchar(32), imageid int4, credit_card_transaction int4, id int4, system_code int4
