FME workspace mdastore1TOcoa-publicdb1_buncombe_tax_inspections.fmw

Parameters:
- SourceDataset_POSTGRES = mda-store-1   # Connection
- DestDataset_POSTGRES = coa-publicdb1   # Connection

Readers:
- POSTGRES_3: POSTGRES from $(SourceDataset_POSTGRES)

Writers:
- POSTGRES_1: POSTGRES to $(DestDataset_POSTGRES)

bc.buncombe_tax_inspections (reader POSTGRES_3)
    attributes: permit_num varchar(30), parcel_num varchar(24), note_date date, year int2, active_flag varchar(1), employee varchar(30), note varchar(100), issue_date date
    -> bc.buncombe_tax_inspections (writer POSTGRES_1)
bc.buncombe_tax_inspections (writer POSTGRES_1)
    attributes: permit_num varchar(30), parcel_num varchar(24), note_date date, year int2, active_flag varchar(1), employee varchar(30), note varchar(100), issue_date date
