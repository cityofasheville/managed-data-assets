FME workspace steepslope_warehouseTOpubrec.fmw

Parameters:
- SourceDataset_POSTGIS = coa-gis-warehouse1   # Connection
- DestDataset_POSTGIS = steepslope   # Connection

Readers:
- POSTGIS_1: POSTGIS from $(SourceDataset_POSTGIS)

Writers:
- POSTGIS_2: POSTGIS to $(DestDataset_POSTGIS)

coagis.bc_incorporated_areas (reader POSTGIS_1)
    attributes: objectid int4,PrimaryKey, area_ numeric(16,5), perimeter numeric(16,5), incorp_ int4, incorp_id int4, distcode varchar(4), description varchar(30)
    -> public.bc_incorporated_areas (writer POSTGIS_2)
public.bc_incorporated_areas (writer POSTGIS_2)
    attributes: objectid int4,PrimaryKey, area_ numeric(16,5), perimeter numeric(16,5), incorp_ int4, incorp_id int4, distcode varchar(4), description varchar(30)
coagis.coa_active_jurisdictions (reader POSTGIS_1)
    attributes: objectid int4,PrimaryKey, areaname varchar(50), acres numeric(38,8), sqmiles numeric(38,8), cityname varchar(9), edit_by varchar(100), jurisdiction_type varchar(150), label varchar(50), edit_date timestamp
    -> public.coa_active_jurisdictions (writer POSTGIS_2)
public.coa_active_jurisdictions (writer POSTGIS_2)
    attributes: objectid int4,PrimaryKey, areaname varchar(50), acres numeric(38,8), sqmiles numeric(38,8), cityname varchar(9), edit_by varchar(100), jurisdiction_type varchar(150), label varchar(50), edit_date timestamp
coagis.bc_property (reader POSTGIS_1)
    attributes: objectid int4,PrimaryKey, pinnum varchar(50), pin varchar(15), pinext varchar(50), owner varchar(50), nmptype varchar(150), taxyear varchar(50), condounit varchar(50), condobuilding varchar(50), deedbook varchar(50), deedpage varchar(50), platbook varchar(50), platpage varchar(50), subname varchar(50), sublot varchar(50), subblock varchar(50), subsect varchar(50), updatedate varchar(50), housenumber varchar(50), numbersuffix varchar(50), direction varchar(50), streetname varchar(50), streettype varchar(50), township varchar(50), acreage numeric(38,8), accountnumber varchar(50), deeddate varchar(50), stamps numeric(38,8), instrument varchar(50), reason varchar(50),
      county varchar(50), city varchar(50), firedistrict varchar(50), schooldistrict varchar(50), careof varchar(50), address varchar(50), cityname varchar(50), state varchar(50), zipcode varchar(50), class varchar(50), improved varchar(50), exempt varchar(50), priced varchar(50), totalmarketvalue numeric(38,8), appraisedvalue numeric(38,8), taxvalue numeric(38,8), landuse varchar(50), neighborhoodcode varchar(50), landvalue numeric(38,8), buildingvalue numeric(38,8), improvementvalue numeric(38,8), appraisalarea varchar(50), state_route varchar(50), state_route_suffix varchar(50), propcard varchar(150), oldpinnum varchar(50), citystatezip varchar(50), deedurl varchar(254), platurl varchar(254)
    -> public.bc_property (writer POSTGIS_2)
public.bc_property (writer POSTGIS_2)
    attributes: objectid int4,PrimaryKey, pinnum varchar(50), pin varchar(15), pinext varchar(50), owner varchar(50), nmptype varchar(150), taxyear varchar(50), condounit varchar(50), condobuilding varchar(50), deedbook varchar(50), deedpage varchar(50), platbook varchar(50), platpage varchar(50), subname varchar(50), sublot varchar(50), subblock varchar(50), subsect varchar(50), updatedate varchar(50), housenumber varchar(50), numbersuffix varchar(50), direction varchar(50), streetname varchar(50), streettype varchar(50), township varchar(50), acreage numeric(38,8), accountnumber varchar(50), deeddate varchar(50), stamps numeric(38,8), instrument varchar(50), reason varchar(50),
      county varchar(50), city varchar(50), firedistrict varchar(50), schooldistrict varchar(50), careof varchar(50), address varchar(50), cityname varchar(50), state varchar(50), zipcode varchar(50), class varchar(50), improved varchar(50), exempt varchar(50), priced varchar(50), totalmarketvalue numeric(38,8), appraisedvalue numeric(38,8), taxvalue numeric(38,8), landuse varchar(50), neighborhoodcode varchar(50), landvalue numeric(38,8), buildingvalue numeric(38,8), improvementvalue numeric(38,8), appraisalarea varchar(50), state_route varchar(50), state_route_suffix varchar(50), propcard varchar(150), oldpinnum varchar(50), citystatezip varchar(50), deedurl varchar(254), platurl varchar(254)
