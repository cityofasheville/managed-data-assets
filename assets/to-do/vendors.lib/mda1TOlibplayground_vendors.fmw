FME workspace mda1TOlibplayground_vendors.fmw

Parameters:
- SourceDataset_POSTGRES = mda-store-1   # Connection
- DestDataset_POSTGRES = library_playground   # Connection

Readers:
- POSTGRES_1: POSTGRES from $(SourceDataset_POSTGRES)

Writers:
- POSTGRES_2: POSTGRES to $(DestDataset_POSTGRES)

internal.vendors (reader POSTGRES_1)
    attributes: a_vendor_id int4, a_vendor_number int4, a_vendor_name varchar(50), v_vend_address1 char(30), v_vend_address2 char(30), v_vend_city char(24), v_vend_state char(2), v_vend_zip char(10), a_vend_alpha_sort char(20), v_dba char(35), v_remit_addrs_y_n char(1), v_vend_entity_cd char(1), v_contact1_name char(20), v_contact1_desc char(10), v_contact1_phone char(20), v_contact1_fax char(20), v_contact2_name char(20), v_contact2_desc char(10), v_contact2_phone char(20), v_contact2_fax char(20), v_vend_status char(1), v_status_reason char(4), v_general_type char(4), v_vendor_class char(4), v_class_notes char(100), v_performance_code char(4), v_geographic_code char(4), v_certif_notes char(100), v_discount_percent numeric(5,3), v_days_disc_remain int2,
      v_days_net int2, v_minimum_order numeric(7,2), v_freight_comment char(20), v_1099_default char(1), v_soc_sec_num varchar(11), v_federal_iv_num varchar(16), a_ar_customer_cid int4, a_employee_number int4, v_bank_code char(3), v_bank_account char(25), v_entry_date timestamp, v_hire_date timestamp, v_w9_sent_y_n char(1), v_w9_received_y_n char(1), v_vend_county char(4), v_freight_percent numeric(5,3), v_email_addrs char(50), v_internet_addrs char(40), v_po_method varchar(1), v_account_type char(1), v_pre_note_for_eft char(1), v_1099_vendor char(1), v_munis_convert varchar(1), v_pay_method char(1), v_email_cont1 char(50), v_email_cont2 char(50), v_name2 char(50), v_do_not_mail varchar(1), v_default_org char(8), v_default_object char(6),
      v_default_proj char(5), v_filler char(50), v_vend_address3 char(30), v_vend_country char(15), v_sep_checks char(1), v_foreign_entity char(1), v_update_clerk char(20), v_update_date timestamp, v_1099_year int2, v_1099_box char(1), v_1099_amount numeric(13,2), v_1099_dept char(6), a_vendor_remit_seq int2, vr_contact_name char(50), vr_vend_seq_addr1 char(30), vr_vend_seq_addr2 char(30), vr_vend_seq_city char(24), vr_vend_seq_state char(2), vr_vend_seq_zip char(10), vr_addr3 char(30), vr_alpha_sort char(20), vr_comment char(30), vr_cont1 char(20), vr_country char(15), vr_duns char(18), vr_email_addr char(50), vr_fax char(20), vr_po_del_meth char(3), vr_state char(2), v_allocation_code int2,
      v_blank_inv char(1), v_class_code char(4), v_county_cd char(4), v_dob timestamp, v_duns char(18), v_dup_inv char(1), v_eft_del_meth char(3), v_eft_file_type char(3), v_salestax_pct numeric(5,3), v_tax_status char(1), v_use_tax char(1), v_usetax_pct numeric(5,3), v_1099_ssn varchar(11), v_po_del_method char(3), v_include_doc char(1), vr_eft_del_meth char(3), apvn_fed_hld char(1), apvn_mbe_wbe char(1), ap99_cusip2 char(13), ap99_cusip1 char(13), v_xml_po char(1), vr_bank_code char(3), vr_bank_account char(25), vr_acct_type char(1), vr_prenote char(1), vr_payment_method char(1), apvn_gender char(30), apvn_ethnicity char(30), apvn_retirement_reportable char(1), apvn_everify_validated char(1),
      v_vend_address4 char(30), a_vendor_name3 char(50), a_vendor_name4 char(50), v_indcont char(1)
    -> r_finance.vendors (writer POSTGRES_2)
r_finance.vendors (writer POSTGRES_2)
    attributes: a_vendor_id int4, a_vendor_number int4, a_vendor_name varchar(50), v_vend_address1 char(30), v_vend_address2 char(30), v_vend_city char(24), v_vend_state char(2), v_vend_zip char(10), a_vend_alpha_sort char(20), v_dba char(35), v_remit_addrs_y_n char(1), v_vend_entity_cd char(1), v_contact1_name char(20), v_contact1_desc char(10), v_contact1_phone char(20), v_contact1_fax char(20), v_contact2_name char(20), v_contact2_desc char(10), v_contact2_phone char(20), v_contact2_fax char(20), v_vend_status char(1), v_status_reason char(4), v_general_type char(4), v_vendor_class char(4), v_class_notes char(100), v_performance_code char(4), v_geographic_code char(4), v_certif_notes char(100), v_discount_percent numeric(5,3), v_days_disc_remain int2,
      v_days_net int2, v_minimum_order numeric(7,2), v_freight_comment char(20), v_1099_default char(1), v_soc_sec_num varchar(11), v_federal_iv_num varchar(16), a_ar_customer_cid int4, a_employee_number int4, v_bank_code char(3), v_bank_account char(25), v_entry_date timestamp, v_hire_date timestamp, v_w9_sent_y_n char(1), v_w9_received_y_n char(1), v_vend_county char(4), v_freight_percent numeric(5,3), v_email_addrs char(50), v_internet_addrs char(40), v_po_method varchar(1), v_account_type char(1), v_pre_note_for_eft char(1), v_1099_vendor char(1), v_munis_convert varchar(1), v_pay_method char(1), v_email_cont1 char(50), v_email_cont2 char(50), v_name2 char(50), v_do_not_mail varchar(1), v_default_org char(8), v_default_object char(6),
      v_default_proj char(5), v_filler char(50), v_vend_address3 char(30), v_vend_country char(15), v_sep_checks char(1), v_foreign_entity char(1), v_update_clerk char(20), v_update_date timestamp, v_1099_year int2, v_1099_box char(1), v_1099_amount numeric(13,2), v_1099_dept char(6), a_vendor_remit_seq int2, vr_contact_name char(50), vr_vend_seq_addr1 char(30), vr_vend_seq_addr2 char(30), vr_vend_seq_city char(24), vr_vend_seq_state char(2), vr_vend_seq_zip char(10), vr_addr3 char(30), vr_alpha_sort char(20), vr_comment char(30), vr_cont1 char(20), vr_country char(15), vr_duns char(18), vr_email_addr char(50), vr_fax char(20), vr_po_del_meth char(3), vr_state char(2), v_allocation_code int2,
      v_blank_inv char(1), v_class_code char(4), v_county_cd char(4), v_dob timestamp, v_duns char(18), v_dup_inv char(1), v_eft_del_meth char(3), v_eft_file_type char(3), v_salestax_pct numeric(5,3), v_tax_status char(1), v_use_tax char(1), v_usetax_pct numeric(5,3), v_1099_ssn varchar(11), v_po_del_method char(3), v_include_doc char(1), vr_eft_del_meth char(3), apvn_fed_hld char(1), apvn_mbe_wbe char(1), ap99_cusip2 char(13), ap99_cusip1 char(13), v_xml_po char(1), vr_bank_code char(3), vr_bank_account char(25), vr_acct_type char(1), vr_prenote char(1), vr_payment_method char(1), apvn_gender char(30), apvn_ethnicity char(30), apvn_retirement_reportable char(1), apvn_everify_validated char(1),
      v_vend_address4 char(30), a_vendor_name3 char(50), a_vendor_name4 char(50), v_indcont char(1)
