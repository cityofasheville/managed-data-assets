FME workspace trackitTOlib_workorders.fmw

Parameters:
- DestDataset_POSTGRES = library_playground   # Connection

Writers:
- POSTGRES_1: POSTGRES to $(DestDataset_POSTGRES)

SQLCreator
    MSSQL_ADO_QUERY_FEATURE_TYPES_FOR_MERGE_FILTERS = Yes
    SQL_STATEMENT:


      	SELECT DISTINCT
      	A.WOID AS id,
      	A.PARENTWOID AS parent_id,
      	children,
      	CASE WHEN children IS NULL THEN 0 ELSE 1 END AS has_children,
      	A.RESPONSEDATE AS respond_by,
      	A.TASK AS title,
      	orig_notes.NoteText description,
      	A.TYPE AS issue_type,
      	A.REQUEST AS requestor,
      	A.REQDATE AS requested_time,
      	A.CLSDDATE AS resolved_time,
      	A.ELAPSETIME AS elapsed_time,
          A.ELAPSEMIN AS elapsed_min,
      	A.PRIORITY AS priority,
      	A.DUEDATE AS due_time,
      	A.RESPONS AS assignee,
      	A.HOURS AS time_spent,
      	A.DEPT AS department,
      	CONVERT(VARCHAR(MAX),A.NOTE) AS resolution,
      	Status.WorkOrderStatusName AS current_status,
      	CASE WHEN children IS NULL THEN A.LOOKUP1 ELSE 'Project' END AS type,
      	A.LOOKUP2 AS hotlist,
      	CASE
      	WHEN A.WO_TEXT1 LIKE 'Top 10%'
      	THEN NULL
      	WHEN A.WO_TEXT1 LIKE '%Top 10%'
      	THEN SUBSTRING(A.WO_TEXT1,2,2)
      	ELSE NULL END	AS rank,
      	CASE
      	WHEN A.WO_TEXT1 LIKE '%Top 10%'
      	THEN RIGHT(RTRIM(A.WO_TEXT1),5)
      	WHEN A.WO_TEXT1 LIKE '%City Need%'
      	THEN RIGHT(RTRIM(A.WO_TEXT1),5)
      	ELSE NULL END	AS period,
      	A.RESPONDEDDATE AS initial_response_time,
      	A.WOTYPE2 AS issue_subtype,
      	A.ASSNDATE AS assigned_time,
      	A.WOTYPE3 AS category
      	FROM TASKS AS A
      	LEFT JOIN (
      		select a1.woid, a1.NoteText
      		FROM (
      			SELECT woid, CONVERT(VARCHAR(MAX),NoteText) NoteText, TaskNoteId
      			FROM dbo.TaskNote
      			LEFT JOIN dbo.TaskNoteCategory
      			ON TaskNote.TaskNoteCategoryId = TaskNoteCategory.TaskNoteCategoryId
      			LEFT JOIN dbo.TaskNoteType
      			ON TaskNote.TaskNoteTypeId = TaskNoteType.TaskNoteTypeId
      			WHERE TaskNoteType.TaskNoteTypeName = 'Incident Description'
      		) AS a1
      		INNER JOIN (
      			SELECT woid, MIN(TaskNoteId) AS MinId
      			FROM dbo.TaskNote
      			LEFT JOIN dbo.TaskNoteCategory
      			ON TaskNote.TaskNoteCategoryId = TaskNoteCategory.TaskNoteCategoryId
      			LEFT JOIN dbo.TaskNoteType
      			ON TaskNote.TaskNoteTypeId = TaskNoteType.TaskNoteTypeId
      			WHERE TaskNoteType.TaskNoteTypeName = 'Incident Description'
      			GROUP BY woid
      		) AS a2
      		on a1.woid = a2.woid
      		AND a1.TaskNoteId = a2.MinId
      	) orig_notes
      	on A.WOID = orig_notes.woid
      	left join TASKS AS children
      	on A.WOID = children.PARENTWOID
      	LEFT JOIN WorkOrderStatus AS Status ON A.WorkOrderStatusId = Status.WorkOrderStatusId
      	LEFT JOIN (
      		SELECT * FROM (
      			SELECT WOID, children = STUFF
      			(
      				(
      					SELECT ',' + CONVERT(VARCHAR(10),WOID)
      					FROM TASKS As T2
      					WHERE T2.PARENTWOID = T1.WOID
      					AND T2.PARENTWOID <> T2.WOID
      					ORDER BY CONVERT(VARCHAR(10),WOID)
      					FOR XML PATH (''), TYPE
      				).value('.', 'varchar(max)')
      			, 1, 1, '')
      			FROM TASKS As T1
      			GROUP BY WOID
      		) inr
      	) AS kids
      	ON A.WOID = kids.WOID
          WHERE A.RESPONS IS NOT NULL
      	order by A.REQDATE desc
    MSSQL_ADO_COMMAND_TIMEOUT = 60
    MSSQL_ADO_NAMED_CONNECTION = TrackIT
    EXPOSED_ATTRIBUTE_LIST = id," parent_id"," children"," has_children"," respond_by"," title"," description"," issue_type"," requestor"," requested_time"," resolved_time"," elapsed_time",elapsed_min," priority"," due_time"," assignee"," time_spent"," department"," resolution"," current_status"," type"," hotlist"," rank"," period"," initial_response_time"," issue_subtype"," assigned_time"," category"
    DATASET = TrackIT
    FORMAT = MSSQL_ADO
    RESULT -> r_it.workorders (writer POSTGRES_1)
r_it.workorders (writer POSTGRES_1)
    attributes: id varchar(200), _parent_id varchar(200), _children varchar(200), _has_children varchar(200), _respond_by varchar(200), _title varchar(200), _description varchar(200), _issue_type varchar(200), _requestor varchar(200), _requested_time varchar(200), _resolved_time varchar(200), _elapsed_time varchar(200), elapsed_min varchar(200), _priority varchar(200), _due_time varchar(200), _assignee varchar(200), _time_spent varchar(200), _department varchar(200), _resolution varchar(200), _current_status varchar(200), _type varchar(200), _hotlist varchar(200), _rank varchar(200), _period varchar(200), _initial_response_time varchar(200), _issue_subtype varchar(200), _assigned_time varchar(200), _category varchar(200)
