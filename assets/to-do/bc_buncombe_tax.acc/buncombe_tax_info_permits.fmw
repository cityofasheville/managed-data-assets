FME workspace buncombe_tax_info_permits.fmw

Parameters:
- SourceDataset_MSSQL_ADO = Accela Prodution Environment   # SQL Server Connection

Readers:
- MSSQL_ADO_1: MSSQL_ADO from $(SourceDataset_MSSQL_ADO)

Note: You are correct! If you replace the SQLExecutors with SQLCreators that will initiate the workspace. SQLExecutors are to be used in a translation that has already been initiated by a reader or creator tranformer / http://docs.safe.com/fme/html/FME_Desktop_Documentation/FME_Transformers/Transformers/sqlcreator.htm
TruncatePopulatePermits: SQLCreator
    SQL_STATEMENT:
      TRUNCATE TABLE [dbo].[BUNCOMBE_TAX_PERMITS]
      EXEC [dbo].[usp_BuncombeTaxPermits]
    MSSQL_ADO_QUERY_FEATURE_TYPES_FOR_MERGE_FILTERS = Yes
    MSSQL_ADO_COMMAND_TIMEOUT = 30
    MSSQL_ADO_NAMED_CONNECTION = Accela Prodution Environment
    FORMAT = MSSQL_ADO
    DATASET = Accela Prodution Environment
