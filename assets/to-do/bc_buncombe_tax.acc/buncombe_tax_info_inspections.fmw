FME workspace buncombe_tax_info_inspections.fmw

Parameters:
- SourceDataset_MSSQL_ADO = Accela Prodution Environment   # SQL Server Connection

Readers:
- MSSQL_ADO_1: MSSQL_ADO from $(SourceDataset_MSSQL_ADO)

TruncatePopulateInspections: SQLCreator
    SQL_STATEMENT:
      TRUNCATE TABLE [dbo].[BUNCOMBE_TAX_INSPECTIONS]
      EXEC [dbo].[usp_BuncombeTaxInspections]
    MSSQL_ADO_QUERY_FEATURE_TYPES_FOR_MERGE_FILTERS = Yes
    MSSQL_ADO_COMMAND_TIMEOUT = 30
    MSSQL_ADO_NAMED_CONNECTION = Accela Prodution Environment
    FORMAT = MSSQL_ADO
    DATASET = Accela Prodution Environment
