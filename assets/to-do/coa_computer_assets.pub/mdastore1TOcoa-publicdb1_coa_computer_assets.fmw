FME workspace mdastore1TOcoa-publicdb1_coa_computer_assets.fmw

Parameters:
- SourceDataset_POSTGRES_2 = mda-store-1   # Connection
- DestDataset_POSTGRES_3 = coa-publicdb1   # Connection

Readers:
- POSTGRES_3: POSTGRES from $(SourceDataset_POSTGRES_2)

Writers:
- POSTGRES_1: POSTGRES to $(DestDataset_POSTGRES_3)

internal.coa_computer_assets (reader POSTGRES_3)
    attributes: ad_account varchar(200), ad_fullname varchar(200), asset_class varchar(200), asset_cost varchar(200), asset_model varchar(200), asset_name varchar(200), asset_serial varchar(200), asset_status varchar(200), bios_name varchar(200), bios_release_date varchar(200), bios_vendor varchar(200), bios_version varchar(200), contact_name varchar(200), cpu_description varchar(200), date_received varchar(200), dept_name varchar(200), hdd_capacity varchar(200), hdd_used varchar(200), ip_address varchar(200), last_boot varchar(200), last_inventory varchar(200), last_user varchar(200), lte_number varchar(200), meid_number varchar(200), office_version varchar(200), os_architecture varchar(200), os_description varchar(200), os_description_trimmed varchar(200), po_number varchar(200), purchased_fy varchar(200),
      ram_gb varchar(200), refurb_date varchar(200), replace_fy varchar(200), service_months varchar(200), system_description varchar(200), tid_number varchar(200), user_full_name varchar(200), user_login_name varchar(200), vendor_name varchar(200), video_controller varchar(200), zap_status varchar(200)
    -> internal.coa_computer_assets (writer POSTGRES_1)
internal.coa_computer_assets (writer POSTGRES_1)
    attributes: ad_account varchar(200), ad_fullname varchar(200), asset_class varchar(200), asset_cost varchar(200), asset_model varchar(200), asset_name varchar(200), asset_serial varchar(200), asset_status varchar(200), bios_name varchar(200), bios_release_date varchar(200), bios_vendor varchar(200), bios_version varchar(200), contact_name varchar(200), cpu_description varchar(200), date_received varchar(200), dept_name varchar(200), hdd_capacity varchar(200), hdd_used varchar(200), ip_address varchar(200), last_boot varchar(200), last_inventory varchar(200), last_user varchar(200), lte_number varchar(200), meid_number varchar(200), office_version varchar(200), os_architecture varchar(200), os_description varchar(200), os_description_trimmed varchar(200), po_number varchar(200), purchased_fy varchar(200),
      ram_gb varchar(200), refurb_date varchar(200), replace_fy varchar(200), service_months varchar(200), system_description varchar(200), tid_number varchar(200), user_full_name varchar(200), user_login_name varchar(200), vendor_name varchar(200), video_controller varchar(200), zap_status varchar(200)
