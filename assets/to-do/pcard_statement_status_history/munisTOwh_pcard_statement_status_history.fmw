FME workspace munisTOwh_pcard_statement_status_history.fmw

Parameters:
- SourceDataset_MSSQL_ADO_3 = munis-prod   # SQL Server Connection
- DestDataset_POSTGRES_3 = mda-store-1   # Connection

Readers:
- MSSQL_ADO_1: MSSQL_ADO from $(SourceDataset_MSSQL_ADO_3)

Writers:
- POSTGRES_2: POSTGRES to $(DestDataset_POSTGRES_3)

amd.pcard_statement_status_history (reader MSSQL_ADO_1)
    attributes: dept_id varchar(2), department varchar(50), div_id varchar(4), division varchar(50), cardholder char(50), statement_code char(10), statement_id integer, statement_status char(1), fiscal_year smallint, fiscal_period smallint, invoiced_date date, reconciled_date date, days_invoiced_to_reconciled integer, approved_date date, days_reconciled_to_approved integer, days_since_invoiced integer, days_since_reconciled integer
    -> internal.pcard_statement_status_history (writer POSTGRES_2)
internal.pcard_statement_status_history (writer POSTGRES_2)
    attributes: dept_id varchar(2), department varchar(50), div_id varchar(4), division varchar(50), cardholder char(50), statement_code char(10), statement_id int4, statement_status char(1), fiscal_year int2, fiscal_period int2, invoiced_date date, reconciled_date date, days_invoiced_to_reconciled int4, approved_date date, days_reconciled_to_approved int4, days_since_invoiced int4, days_since_reconciled int4
