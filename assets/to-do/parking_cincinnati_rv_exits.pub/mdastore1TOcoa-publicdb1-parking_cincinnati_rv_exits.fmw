FME workspace mdastore1TOcoa-publicdb1-parking_cincinnati_rv_exits.fmw

Parameters:
- SourceDataset_POSTGRES = mda-store-1   # Connection
- DestDataset_POSTGRES = coa-publicdb1   # Connection

Readers:
- POSTGRES_1: POSTGRES from $(SourceDataset_POSTGRES)

Writers:
- POSTGRES_2: POSTGRES to $(DestDataset_POSTGRES)

internal.parking_cincinnati_rv_exits (reader POSTGRES_1)
    attributes: transaction_stamp varchar(40), device_key varchar(20), machine_number int2, device_type int2, central_pay int2, firmware int2, attendant int2, attendant_override int2, entry_time timestamp, exit_time timestamp, transaction_number int4, transaction_type int2, central_pay_sent int2, complimentary int2, validated int2, ticket int8, ticket_type varchar(2), dispenser int2, rate varchar(2), rate_type int2, gross float8, net float8, cash_amount float8, tendered float8, short_money float8, change float8, currency_type int2, exchange float8, num_val int2, misc_key int2,
      misc_amount float8, tax float8, tax_overruled int2, card_type int2, card_number int4, card_amount float8, check_number int4, check_amount float8, num_discount int2, amt_discount float8, exit_count int2, payment_type int2
    -> smarking.parking_cincinnati_rv_exits (writer POSTGRES_2)
smarking.parking_cincinnati_rv_exits (writer POSTGRES_2)
    attributes: transaction_stamp varchar(40), device_key varchar(20), machine_number int2, device_type int2, central_pay int2, firmware int2, attendant int2, attendant_override int2, entry_time timestamp, exit_time timestamp, transaction_number int4, transaction_type int2, central_pay_sent int2, complimentary int2, validated int2, ticket int8, ticket_type varchar(2), dispenser int2, rate varchar(2), rate_type int2, gross float8, net float8, cash_amount float8, tendered float8, short_money float8, change float8, currency_type int2, exchange float8, num_val int2, misc_key int2,
      misc_amount float8, tax float8, tax_overruled int2, card_type int2, card_number int4, card_amount float8, check_number int4, check_amount float8, num_discount int2, amt_discount float8, exit_count int2, payment_type int2
