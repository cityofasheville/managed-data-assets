FME workspace avl_dashboard_SLA_first_review_data.fmw

Parameters:
- SourceDataset_MSSQL_ADO = AccelaDB   # SQL Server Connection
- DestDataset_POSTGRES = coa-pg-db1-datastore1   # Connection

Readers:
- MSSQL_ADO_1: MSSQL_ADO from $(SourceDataset_MSSQL_ADO)

Writers:
- POSTGRES_1: POSTGRES to $(DestDataset_POSTGRES)

dbo.avl_dashboard_SLA_first_review_data (reader MSSQL_ADO_1)
    attributes: RecordId varchar(30), FirstDate bigint, RecordType varchar(255), Group varchar(30), Type varchar(30), SubType varchar(30), Category varchar(30), Task varchar(100), TaskStatus varchar(200), SLADesc varchar(4000), Start varchar(30), SLA numeric(28,1), DUE varchar(30), FirstPlanReviewedDate varchar(30), Month integer, year integer, MetSLA varchar(1), SLABusiness integer, WorkedDaysBusiness integer
    -> amd.avl_dashboard_SLA_first_review_data (writer POSTGRES_1)
amd.avl_dashboard_SLA_first_review_data (writer POSTGRES_1)
    attributes: recordid varchar(30), firstdate int8, recordtype varchar(255), group varchar(30), type varchar(30), subtype varchar(30), category varchar(30), task varchar(100), taskstatus varchar(200), sladesc varchar(4000), start varchar(30), sla numeric(28,1), due varchar(30), firstplanrevieweddate varchar(30), month int4, year int4, metsla varchar(1), slabusiness int4, workeddaysbusiness int4
