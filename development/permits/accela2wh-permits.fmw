FME workspace accela2wh-permits.fmw

Parameters:
- SourceDataset_MSSQL_ADO = @coa-dscdb/accelaprod   # SQL Server Connection
- DestDataset_POSTGRES_3 = datastore1   # Connection

Readers:
- MSSQL_ADO_1: MSSQL_ADO from $(SourceDataset_MSSQL_ADO)

Writers:
- POSTGRES_2: POSTGRES to $(DestDataset_POSTGRES_3)

amd.permits (reader MSSQL_ADO_1)
    attributes: permit_num varchar(30), permit_group varchar(30), permit_type varchar(30), permit_subtype varchar(30), permit_category varchar(30), applicant_name varchar(255), permit_description varchar(4000), applied_date datetime, status_current varchar(30), status_date datetime, created_by varchar(100), building_value varchar(500), job_value float, total_project_valuation varchar(500), total_sq_feet varchar(500), fees numeric(15,2), paid numeric(15,2), balance numeric(15,2), invoiced_fee_total float, civic_address_id varchar(50), record_id varchar(17)
    -> amd.permits (writer POSTGRES_2)
amd.permits (writer POSTGRES_2)
    attributes: permit_num varchar(30), permit_group varchar(30), permit_type varchar(30), permit_subtype varchar(30), permit_category varchar(30), applicant_name varchar(255), permit_description varchar(4000), applied_date timestamp, status_current varchar(30), status_date timestamp, created_by varchar(100), building_value varchar(500), job_value float8, total_project_valuation varchar(500), total_sq_feet varchar(500), fees numeric(15,2), paid numeric(15,2), balance numeric(15,2), invoiced_fee_total float8, civic_address_id varchar(50), record_id varchar(17)
