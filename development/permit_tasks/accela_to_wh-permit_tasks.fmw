FME workspace accela_to_wh-permit_tasks.fmw

Parameters:
- SourceDataset_MSSQL_ADO = @coa-dscdb/accelaprod   # SQL Server Connection
- DestDataset_POSTGRES = datastore1   # Connection

Readers:
- MSSQL_ADO_1: MSSQL_ADO from $(SourceDataset_MSSQL_ADO)

Writers:
- POSTGRES_1: POSTGRES to $(DestDataset_POSTGRES)

amd.permit_tasks (reader MSSQL_ADO_1)
    attributes: permit_num varchar(30), permit_group varchar(100), permit_type varchar(30), permit_subtype varchar(30), permit_category varchar(30), process_code varchar(70), task varchar(100), task_status varchar(200), current_status_date datetime, step_number nvarchar(10), relation_sequence_id nvarchar(10), parent_task_name varchar(155), user_name varchar(141), user_id varchar(70), user_department varchar(80), due_date datetime, record_date datetime, comments varchar(4000), is_completed varchar(1), is_active varchar(1), assigned_date datetime, assigned_user varchar(141), assigned_department varchar(80), process_history_sequence_number bigint, record_id varchar(17)
    -> amd.permit_tasks (writer POSTGRES_1)
amd.permit_tasks (writer POSTGRES_1)
    attributes: permit_num varchar(30), permit_group varchar(100), permit_type varchar(30), permit_subtype varchar(30), permit_category varchar(30), process_code varchar(70), task varchar(100), task_status varchar(200), current_status_date timestamp, step_number varchar(10), relation_sequence_id varchar(10), parent_task_name varchar(155), user_name varchar(141), user_id varchar(70), user_department varchar(80), due_date timestamp, record_date timestamp, comments varchar(4000), is_completed varchar(1), is_active varchar(1), assigned_date timestamp, assigned_user varchar(141), assigned_department varchar(80), process_history_sequence_number int8, record_id varchar(17)
