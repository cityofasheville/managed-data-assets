FME workspace accelaTOwh-permit_comments.fmw

Parameters:
- SourceDataset_MSSQL_ADO = @coa-dscdb/accelaprod   # SQL Server Connection
- DestDataset_POSTGRES = mda-store-1   # Connection

Readers:
- MSSQL_ADO_1: MSSQL_ADO from $(SourceDataset_MSSQL_ADO)

Writers:
- POSTGRES_2: POSTGRES to $(DestDataset_POSTGRES)

amd.permit_comments (reader MSSQL_ADO_1)
    attributes: permit_num varchar(30), comment_seq_number bigint, comment_date datetime, comments text
    -> public.permit_comments (writer POSTGRES_2)
public.permit_comments (writer POSTGRES_2)
    attributes: permit_num varchar(30), comment_seq_number int8, comment_date timestamp, comments text
