FME workspace bun2wh-bc_location.fmw

Parameters:
- DestDataset_POSTGIS = coa-pg-db1-datastore1   # Connection

Readers:
- GEODATABASE_SDE_1: GEODATABASE_SDE

Writers:
- POSTGIS_1: POSTGIS to $(DestDataset_POSTGIS)

DBO.location (reader GEODATABASE_SDE_1)
    attributes: OBJECTID integer, LOCATION_ID double, LOCATIONTYPE integer, CIVICADDRESS_ID double, PARENT_LOCATION_ID double, BUILDING_ID double, CENTERLINE_ID double, USER_ID char(8), ESN smallint, X_COORD double, Y_COORD double, COMMCODE char(4), PRIMARY_STRUCTURE smallint, CREATE_DATE date, CHANGE_DATE date, PARCEL_ID char(10)
    -> CreateDateFormatter
CreateDateFormatter: DateFormatter
    SRCFMT = Unknown - Automatic Detection
    FMT = FME Date/Time (%Y%m%d%H%M%S)
    DATE_ATTR = CREATE_DATE
    INVALID_DATE_VALUE = _FME_NO_OP_
    -> amd.bc_location (writer POSTGIS_1)
amd.bc_location (writer POSTGIS_1)
    attributes: objectid int4, location_id float8, locationtype int4, civicaddress_id float8, parent_location_id float8, building_id float8, centerline_id float8, user_id varchar(8), esn int2, x_coord float8, y_coord float8, commcode varchar(4), primary_structure int2, create_date timestamp, change_date timestamp, parcel_id varchar(10)
