FME workspace google2wh-capital_projects_master.fmw

Parameters:
- DestDataset_POSTGRES = datastore1   # Connection

Readers:
- GOOGLESHEETS_2: GOOGLESHEETS
- GOOGLESHEETS_1: GOOGLESHEETS

Writers:
- GEODATABASE_SDE_1: GEODATABASE_SDE
- POSTGRES_1: POSTGRES to $(DestDataset_POSTGRES)

General Project Information (reader GOOGLESHEETS_2)
    attributes: GIS_ID text, MUNIS Project Number text, Project text, Display Name text, Location Details text, Zip Code text, Type text, Category text, COA Contact text, Phone Number text, Email Address text, Owner Department text, Administering Department text, Project Description text, Map Tab text, Status text, Total Project Funding (Budget Document) text, Target Construction Start text, Target Construction End text, Actual Construction End text, Amount behind Schedule text, Estimated Construction Duration text, Project Folder text, Project Webpage (more information) text, Communication Plan text, Photo URL text, Project Updates text
    -> amd.capital_projects_master (writer GEODATABASE_SDE_1)
amd.capital_projects_master (writer GEODATABASE_SDE_1)
    attributes: gis_id char(2048), munis_project_number char(2048), project char(2048), display_name char(2048), location_details char(2048), zip_code char(2048), type char(2048), category char(2048), coa_contact char(2048), phone_number char(2048), email_address char(2048), owner_department char(2048), administering_department char(2048), project_description char(2048), map_tab char(2048), status char(2048), total_project_funding_budget_d char(2048), target_construction_start char(2048), target_construction_end char(2048), actual_construction_end char(2048), amount_behind_schedule char(2048), estimated_construction_duratio char(2048), project_folder char(2048), project_webpage_more_informati char(2048), communication_plan char(2048), photo_url char(2048), project_updates char(2048)
Categories (reader GOOGLESHEETS_1)
    attributes: Category Name text, Display Order text
    -> amd.capital_projects_master_categories (writer POSTGRES_1)
amd.capital_projects_master_categories (writer POSTGRES_1)
    attributes: category_name text, display_order text
