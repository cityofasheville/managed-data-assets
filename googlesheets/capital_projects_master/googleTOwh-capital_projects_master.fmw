FME workspace googleTOwh-capital_projects_master.fmw

Parameters:
- DestDataset_POSTGRES_3 = mda-store-1   # Connection

Readers:
- GOOGLESHEETS_1: GOOGLESHEETS
- GOOGLESHEETS_2: GOOGLESHEETS

Writers:
- POSTGRES_1: POSTGRES to $(DestDataset_POSTGRES_3)

General Project Information (reader GOOGLESHEETS_1)
    attributes: GIS_ID text, MUNIS Project Number text, Project text, Display Name text, Location Details text, Zip Code text, Type text, Category text, COA Contact text, Phone Number text, Email Address text, Owner Department text, Administering Department text, Project Description text, Map Tab text, Status text, Total Project Funding (Budget Document) text, Target Construction Start text, Target Construction End text, Actual Construction End text, Amount behind Schedule text, Estimated Construction Duration text, Project Folder text, Project Webpage (more information) text, Communication Plan text, Photo URL text, Project Updates text
    -> capital_projects_master (writer POSTGRES_1)
capital_projects_master (writer POSTGRES_1)
    attributes: gis_id text, munis_project_number text, project text, display_name text, location_details text, zip_code text, type text, category text, coa_contact text, phone_number text, email_address text, owner_department text, administering_department text, project_description text, map_tab text, status text, total_project_funding__budget_document_ text, target_construction_start text, target_construction_end text, actual_construction_end text, amount_behind_schedule text, estimated_construction_duration text, project_folder text, project_webpage__more_information_ text, communication_plan text, photo_url text, project_updates text
Categories (reader GOOGLESHEETS_2)
    attributes: Category Name text, Display Order text
    -> capital_projects_master_categories (writer POSTGRES_1)
capital_projects_master_categories (writer POSTGRES_1)
    attributes: category_name text, display_order text
