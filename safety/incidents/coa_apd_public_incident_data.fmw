FME workspace coa_apd_public_incident_data.fmw

Parameters:
- SourceDataset_POSTGIS = coa-gis-warehouse1b   # Connection
- DestDataset_POSTGIS = coa-pg-db1   # Connection

Readers:
- POSTGIS_1: POSTGIS from $(SourceDataset_POSTGIS)

Writers:
- POSTGIS_2: POSTGIS to $(DestDataset_POSTGIS)

coagis.coa_apd_public_incidents_view (reader POSTGIS_1)
    attributes: objectid int4, incident_id int4, agency varchar(4), date_occurred timestamp, case_number varchar(12), address varchar(75), geo_beat varchar(4), geo_report_area varchar(4), x numeric(38,8), y numeric(38,8), offense_short_description varchar(25), offense_long_description varchar(60), offense_code varchar(4), offense_group_code varchar(50), offense_group_level varchar(50), offense_group_short_description varchar(100), offense_group_long_description varchar(254)
    -> amd.coa_apd_public_incidents_view (writer POSTGIS_2)
amd.coa_apd_public_incidents_view (writer POSTGIS_2)
    attributes: objectid int4, incident_id int4, agency varchar(4), date_occurred timestamp, case_number varchar(12), address varchar(75), geo_beat varchar(4), geo_report_area varchar(4), x numeric(38,8), y numeric(38,8), offense_short_description varchar(25), offense_long_description varchar(60), offense_code varchar(4), offense_group_code varchar(50), offense_group_level varchar(50), offense_group_short_description varchar(100), offense_group_long_description varchar(254)
