FME workspace bc_public_incident_data.fmw

Parameters:
- SourceDataset_MSSQL_ADO = RMS   # SQL Server Connection
- DestDataset_POSTGRES = mda-store-1   # Connection

Readers:
- MSSQL_ADO_1: MSSQL_ADO from $(SourceDataset_MSSQL_ADO)

Writers:
- GEODATABASE_SDE_1: GEODATABASE_SDE
- POSTGRES_1: POSTGRES to $(DestDataset_POSTGRES)

uvw_public_incident_data (reader MSSQL_ADO_1)
    attributes: incident_id integer, agency char(4), date_occurred datetime, case_number varchar(12), address varchar(75), geo_beat char(4), geo_report_area char(4), geo_x numeric(13,2), geo_y numeric(13,2), offense_short_description varchar(25), offense_long_description varchar(60), offense_code char(4), offense_group_code nvarchar(50), offense_group_level nvarchar(50), offense_group_short_description nvarchar(100), offense_group_long_description nvarchar(1000)
    -> Counter
Counter
    CNT_ATTR = _count
    START = 0
    DOMAIN = counter
    SCOPE = Global
    -> bc_public_incident_data (writer POSTGRES_1)
bc_public_incident_data (writer POSTGRES_1)
    attributes: incident_id int4, agency char(4), date_occurred timestamp, case_number varchar(12), address varchar(75), geo_beat char(4), geo_report_area char(4), geo_x numeric(13,2), geo_y numeric(13,2), offense_short_description varchar(25), offense_long_description varchar(60), offense_code char(4), offense_group_code varchar(50), offense_group_level varchar(50), offense_group_short_description varchar(100), offense_group_long_description varchar(1000), _count varchar(200)
