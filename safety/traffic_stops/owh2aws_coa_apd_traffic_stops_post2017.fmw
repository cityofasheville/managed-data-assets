FME workspace owh2aws_coa_apd_traffic_stops_post2017.fmw

Parameters:
- SourceDataset_POSTGRES = coa-gis-warehouse1   # Connection
- SourceDataset_POSTGIS = coa-gis-warehouse1b   # Connection
- DestDataset_POSTGIS = PublicOpenDataAWS   # Connection

Readers:
- POSTGRES_1: POSTGRES from $(SourceDataset_POSTGRES)
- POSTGIS_1: POSTGIS from $(SourceDataset_POSTGIS)

Writers:
- POSTGIS_2: POSTGIS to $(DestDataset_POSTGIS)

coagis.coa_apd_traffic_stops_post2017 (reader POSTGIS_1)
    attributes: traffic_stop_id int4, objectid int4, agency char(4), date_occurred timestamp, address varchar(75), stop_sbi_desc varchar(29), consent_by_code char(4), cons_code_desc varchar(55), rsn_cons_code char(4), rsn_cons_desc varchar(55), enf_code_sbi varchar(15), driver_arrested int2, passenger_arrested int2, off_phys_resis int2, off_use_force int2, inj_officer int2, inj_driver int2, inj_passgr int2, search_initiated int2, t_search_consent int2, t_search_warrant int2, t_probable_cause int2, t_inc_arrest int2, t_pro_frisk int2, b_err_susp_bhvr int2, b_obs_susp_cband int2, b_sus_o_off_info int2, b_sus_movemt int2, b_infomt_tip int2, b_witness_obs int2,
      vehicle_searched int2, driver_searched int2, passenger_searched int2, personal_effects_searched int2, no_contraband_found int2, geo_beat char(4), geo_report_area char(4), sbi_submission_date timestamp, sbi_resubmission_flag int2
    -> amd.coa_apd_traffic_stops_post2017 (writer POSTGIS_2)
amd.coa_apd_traffic_stops_post2017 (writer POSTGIS_2)
    attributes: traffic_stop_id int4, objectid int4, agency char(4), date_occurred timestamp, address varchar(75), stop_sbi_desc varchar(29), consent_by_code char(4), cons_code_desc varchar(55), rsn_cons_code char(4), rsn_cons_desc varchar(55), enf_code_sbi varchar(15), driver_arrested int2, passenger_arrested int2, off_phys_resis int2, off_use_force int2, inj_officer int2, inj_driver int2, inj_passgr int2, search_initiated int2, t_search_consent int2, t_search_warrant int2, t_probable_cause int2, t_inc_arrest int2, t_pro_frisk int2, b_err_susp_bhvr int2, b_obs_susp_cband int2, b_sus_o_off_info int2, b_sus_movemt int2, b_infomt_tip int2, b_witness_obs int2,
      vehicle_searched int2, driver_searched int2, passenger_searched int2, personal_effects_searched int2, no_contraband_found int2, geo_beat char(4), geo_report_area char(4), sbi_submission_date timestamp, sbi_resubmission_flag int2
