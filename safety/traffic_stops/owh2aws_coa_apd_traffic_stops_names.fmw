FME workspace owh2aws_coa_apd_traffic_stops_names.fmw

Parameters:
- SourceDataset_POSTGRES = coa-gis-warehouse1b   # Connection
- DestDataset_POSTGRES = PublicOpenDataAWS   # Connection

Readers:
- POSTGRES_1: POSTGRES from $(SourceDataset_POSTGRES)

Writers:
- POSTGRES_2: POSTGRES to $(DestDataset_POSTGRES)

coagis.coa_apd_traffic_stop_name_data_table (reader POSTGRES_1)
    attributes: traffic_stop_id int4, name_type char(4), name_type_sequence int2, name_age char(2), name_race char(2), name_sex char(1), name_ethnicity char(1), traffic_stop_name_id int4, objectid serial,PRIKEY
    -> amd.coa_apd_traffic_stop_name_data_table (writer POSTGRES_2)
amd.coa_apd_traffic_stop_name_data_table (writer POSTGRES_2)
    attributes: traffic_stop_id int4, name_type char(4), name_type_sequence int2, name_age char(2), name_race char(2), name_sex char(1), name_ethnicity char(1), traffic_stop_name_id int4, objectid serial,PRIKEY
