FME workspace bc_apd_traffic_stopes.fmw

Parameters:
- DestDataset_POSTGRES = coa-gis-warehouse1b   # Connection
- DestDataset_POSTGRES_3 = coa-gis-warehouse1b   # Connection
- SourceDataset_POSTGIS = coa-gis-warehouse1b   # Connection
- SourceDataset_MSSQL_ADO_5 = RMS   # SQL Server Connection
- SourceDataset_MSSQL_ADO = rmsdev   # SQL Server Connection

Readers:
- POSTGIS_1: POSTGIS from $(SourceDataset_POSTGIS)
- MSSQL_ADO_1: MSSQL_ADO from $(SourceDataset_MSSQL_ADO_5)
- MSSQL_ADO_2: MSSQL_ADO from $(SourceDataset_MSSQL_ADO)

Writers:
- POSTGRES_1: POSTGRES to $(DestDataset_POSTGRES)
- POSTGRES_2: POSTGRES to $(DestDataset_POSTGRES_3)
- GEODATABASE_SDE_1: GEODATABASE_SDE
- GEODATABASE_SDE_2: GEODATABASE_SDE
- ARCGISONLINEFEATURES_1: ARCGISONLINEFEATURES

uvw_apd_traffic_stop_data (reader MSSQL_ADO_1) [off]
    attributes: agency char(4), case_number varchar(12), date_occurred datetime, address varchar(75), initial_purpose_of_stop_code char(4), initial_purpose_of_stop_code_description varchar(55), initial_purpose_of_stop_sbi_description varchar(29), consent_by_code char(4), consent_by_code_description varchar(55), reason_consent_requested_code char(4), reason_consent_requested_code_description varchar(55), enforcement_action_code char(4), enforcement_action_code_description varchar(55), enforcement_action_code_sbi_description varchar(15), driver_arrested tinyint, passenger_arrested tinyint, officer_encountered_physical_resistance tinyint, officer_engaged_in_use_of_force tinyint, injuries_occurred_to_officer tinyint, injuries_occurred_to_driver tinyint, injurires_occurred_to_passenger tinyint, search_initiated tinyint, type_of_search_consent tinyint, type_of_search_search_warrant tinyint, type_of_search_probable_cause tinyint, type_of_search_incident_to_arrest tinyint, type_of_search_protective_frisk tinyint, basis_for_search_erratic_suspicious_behavior tinyint, basis_for_search_observation_of_suspected_contraband tinyint, basis_for_search_suspicious_other_official_information tinyint,
      basis_for_search_suspicious_movement tinyint, basis_for_search_informant_tip tinyint, basis_for_search_witness_observation tinyint, vehicle_searched tinyint, driver_searched tinyint, passenger_searched tinyint, personal_effects_searched tinyint, no_contraband_found tinyint, geo_beat char(4), geo_report_area char(4), geo_x numeric(13,2), geo_y numeric(13,2), incident_id integer, traffic_stop_id integer, sbi_submission_date datetime, sbi_resubmission_flag tinyint
    -> Counter_3
uvw_apd_traffic_stop_name_data (reader MSSQL_ADO_1)
    attributes: traffic_stop_id integer, name_type char(4), name_type_sequence tinyint, name_age char(2), name_race char(2), name_sex char(1), name_ethnicity char(1), traffic_stop_name_id identity
    -> Counter_2
Counter_2
    DOMAIN = counter
    CNT_ATTR = _count
    START = 0
    SCOPE = Global
    -> coa_apd_traffic_stop_name_data_table (writer POSTGRES_1)
coa_apd_traffic_stop_name_data_table (writer POSTGRES_1)
    attributes: traffic_stop_id int4, name_type char(4), name_type_sequence int2, name_age char(2), name_race char(2), name_sex char(1), name_ethnicity char(1), traffic_stop_name_id int4, objectid serial,PRIKEY
coa_apd_traffic_stop_data_view (reader POSTGIS_1)
    attributes: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
bc_street_midpoint_view (reader POSTGIS_1)
    attributes: objectid int4, centerline_id numeric(38,8)
dbo.uvw_apd_traffic_stop_data (reader MSSQL_ADO_2)
    attributes: agency char(4), case_number varchar(12), date_occurred datetime, address varchar(75), initial_purpose_of_stop_code char(4), initial_purpose_of_stop_code_description varchar(55), initial_purpose_of_stop_sbi_description varchar(29), consent_by_code char(4), consent_by_code_description varchar(55), reason_consent_requested_code char(4), reason_consent_requested_code_description varchar(55), enforcement_action_code char(4), enforcement_action_code_description varchar(55), enforcement_action_code_sbi_description varchar(15), driver_arrested tinyint, passenger_arrested tinyint, officer_encountered_physical_resistance tinyint, officer_engaged_in_use_of_force tinyint, injuries_occurred_to_officer tinyint, injuries_occurred_to_driver tinyint, injurires_occurred_to_passenger tinyint, search_initiated tinyint, type_of_search_consent tinyint, type_of_search_search_warrant tinyint, type_of_search_probable_cause tinyint, type_of_search_incident_to_arrest tinyint, type_of_search_protective_frisk tinyint, basis_for_search_erratic_suspicious_behavior tinyint, basis_for_search_observation_of_suspected_contraband tinyint, basis_for_search_suspicious_other_official_information tinyint,
      basis_for_search_suspicious_movement tinyint, basis_for_search_informant_tip tinyint, basis_for_search_witness_observation tinyint, vehicle_searched tinyint, driver_searched tinyint, passenger_searched tinyint, personal_effects_searched tinyint, no_contraband_found tinyint, geo_beat char(4), geo_report_area char(4), geo_x numeric(13,2), geo_y numeric(13,2), incident_id integer, traffic_stop_id integer, sbi_submission_date datetime, sbi_resubmission_flag tinyint
    -> Counter_3
Counter_3
    DOMAIN = counter
    CNT_ATTR = _count
    START = 0
    SCOPE = Global
    -> coa_apd_traffic_stop_data_table (writer POSTGRES_2)
coa_apd_traffic_stop_data_table (writer POSTGRES_2)
    attributes: agency char(4), case_number varchar(12), date_occurred timestamp, address varchar(75), initial_purpose_of_stop_code char(4), initial_purpose_of_stop_code_description varchar(55), initial_purpose_of_stop_sbi_description varchar(29), consent_by_code char(4), consent_by_code_description varchar(55), reason_consent_requested_code char(4), reason_consent_requested_code_description varchar(55), enforcement_action_code char(4), enforcement_action_code_description varchar(55), enforcement_action_code_sbi_description varchar(15), driver_arrested int2, passenger_arrested int2, officer_encountered_physical_resistance int2, officer_engaged_in_use_of_force int2, injuries_occurred_to_officer int2, injuries_occurred_to_driver int2, injurires_occurred_to_passenger int2, search_initiated int2, type_of_search_consent int2, type_of_search_search_warrant int2, type_of_search_probable_cause int2, type_of_search_incident_to_arrest int2, type_of_search_protective_frisk int2, basis_for_search_erratic_suspicious_behavior int2, basis_for_search_observation_of_suspected_contraband int2, basis_for_search_suspicious_other_official_information int2,
      basis_for_search_suspicious_movement int2, basis_for_search_informant_tip int2, basis_for_search_witness_observation int2, vehicle_searched int2, driver_searched int2, passenger_searched int2, personal_effects_searched int2, no_contraband_found int2, geo_beat char(4), geo_report_area char(4), geo_x numeric(13,2), geo_y numeric(13,2), incident_id int4, traffic_stop_id int4, sbi_submission_date timestamp, sbi_resubmission_flag int2, objectid serial,PRIKEY
SQLCreator
    POSTGIS_DISABLE_COLLECTION_SPLITTING = yes
    POSTGIS_SCHEMAS_FOR_TABLE_LISTING = coagis
    FORMAT = POSTGIS
    POSTGIS_NAMED_CONNECTION = coa-gis-warehouse1b
    POSTGIS_USE_TRUE_POSTGIS_TYPES = yes
    DATASET = coa-gis-warehouse1b
    EXPOSED_ATTRIBUTE_LIST = address,agency,b_err_susp_bhvr,b_infomt_tip,b_obs_susp_cband,b_sus_movemt,b_sus_o_off_info,b_witness_obs,case_number,cons_code_desc,consent_by_code,date_occurred,driver_arrested,driver_searched,enf_action_code,enf_code_desc,enf_code_sbi,geo_beat,geo_report_area,incident_id,inj_driver,inj_officer,inj_passgr,name_age,name_ethnicity,name_race,name_sex,name_type,name_type_sequence,no_contraband_found,objectid,off_phys_resis,off_use_force,passenger_arrested,passenger_searched,personal_effects_searched,rsn_cons_code,rsn_cons_desc,sbi_resubmission_flag,sbi_submission_date,search_initiated,stop_sbi_desc,stopcode,stopcode_desc,t_inc_arrest,t_pro_frisk,t_probable_cause,t_search_consent,t_search_warrant,traffic_stop_id,traffic_stop_name_id,vehicle_searched
    POSTGIS_QUERY_FEATURE_TYPES_FOR_MERGE_FILTERS = Yes
    SQL_STATEMENT:
      SELECT traffic.traffic_stop_id, traffic.objectid, traffic.agency,
      --traffic.case_number,
      traffic.date_occurred,
      traffic.address,
      --traffic.stopcode,
      --traffic.stopcode_desc,
      traffic.stop_sbi_desc,
      traffic.consent_by_code,
      traffic.cons_code_desc,
      traffic.rsn_cons_code,
      traffic.rsn_cons_desc,
      --traffic.enf_action_code,
      --traffic.enf_code_desc,
      traffic.enf_code_sbi,
      traffic.driver_arrested,
      traffic.passenger_arrested,
      traffic.off_phys_resis,
      traffic.off_use_force,
      traffic.inj_officer,
      traffic.inj_driver,
      traffic.inj_passgr,
      traffic.search_initiated,
      traffic.t_search_consent,
      traffic.t_search_warrant,
      traffic.t_probable_cause,
      traffic.t_inc_arrest,
      traffic.t_pro_frisk,
      traffic.b_err_susp_bhvr,
      traffic.b_obs_susp_cband,
      traffic.b_sus_o_off_info,
      traffic.b_sus_movemt,
      traffic.b_infomt_tip,
      traffic.b_witness_obs,
      traffic.vehicle_searched,
      traffic.driver_searched,
      traffic.passenger_searched,
      traffic.personal_effects_searched,
      traffic.no_contraband_found,
      traffic.geo_beat,
      traffic.geo_report_area,
      --traffic.incident_id,
      traffic.sbi_submission_date,
      traffic.sbi_resubmission_flag,
      --traffic.traffic_stop_name_id,
      --traffic.name_type,
      --traffic.name_type_sequence,
      --traffic.name_age,
      --traffic.name_race,
      --traffic.name_sex,
      --traffic.name_ethnicity,
             ST_Snap(
                 traffic.shape,
                 ST_ClosestPoint(street.shape, traffic.shape),
                 ST_Distance(
                     traffic.shape,
                     ST_ClosestPoint(street.shape, traffic.shape)
                  ) * 1.01
              ) AS shape2
      FROM (
          SELECT ST_Collect(shape) as shape
          FROM bc_street_midpoint_view
      ) AS street,
      coa_apd_traffic_stop_data_view AS traffic
    RESULT -> coa_apd_traffic_stops (writer GEODATABASE_SDE_2)
coa_apd_traffic_stops (writer GEODATABASE_SDE_2)
    attributes: objectid integer, address char(200), agency char(200), b_err_susp_bhvr char(200), b_infomt_tip char(200), b_obs_susp_cband char(200), b_sus_movemt char(200), b_sus_o_off_info char(200), b_witness_obs char(200), case_number char(200), cons_code_desc char(200), consent_by_code char(200), date_occurred char(200), driver_arrested char(200), driver_searched char(200), enf_action_code char(200), enf_code_desc char(200), enf_code_sbi char(200), geo_beat char(200), geo_report_area char(200), incident_id char(200), inj_driver char(200), inj_officer char(200), inj_passgr char(200), name_age char(200), name_ethnicity char(200), name_race char(200), name_sex char(200), name_type char(200), name_type_sequence char(200),
      no_contraband_found char(200), off_phys_resis char(200), off_use_force char(200), passenger_arrested char(200), passenger_searched char(200), personal_effects_searched char(200), rsn_cons_code char(200), rsn_cons_desc char(200), sbi_resubmission_flag char(200), sbi_submission_date char(200), search_initiated char(200), stop_sbi_desc char(200), stopcode char(200), stopcode_desc char(200), t_inc_arrest char(200), t_pro_frisk char(200), t_probable_cause char(200), t_search_consent char(200), t_search_warrant char(200), traffic_stop_id char(200), traffic_stop_name_id char(200), vehicle_searched char(200)
APD Traffic Stops pre-Oct 2017 (writer ARCGISONLINEFEATURES_1)
    attributes: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
APD Traffic Stops after Oct 1 2017 (writer ARCGISONLINEFEATURES_1)
    attributes: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
APDTraffic Stop Name Data Table (writer ARCGISONLINEFEATURES_1)
    attributes: traffic_stop_id esriFieldTypeInteger, name_type esriFieldTypeString(4), name_type_sequence esriFieldTypeSmallInteger, name_age esriFieldTypeString(2), name_race esriFieldTypeString(2), name_sex esriFieldTypeString(1), name_ethnicity esriFieldTypeString(1), objectid esriFieldTypeOID
